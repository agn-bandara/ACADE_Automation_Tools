Attribute VB_Name = "Module1"
Declare PtrSafe Sub Sleep Lib "kernel32" (ByVal dwMilliseconds As Long)
#If VBA7 Then
    Declare PtrSafe Function GlobalUnlock Lib "kernel32" (ByVal hMem As LongPtr) As Long
    Declare PtrSafe Function GlobalLock Lib "kernel32" (ByVal hMem As LongPtr) As LongPtr
    Declare PtrSafe Function GlobalAlloc Lib "kernel32" (ByVal wFlags As Long, ByVal dwBytes As Long) As LongPtr
    Declare PtrSafe Function CloseClipboard Lib "user32" () As Long
    Declare PtrSafe Function OpenClipboard Lib "user32" (ByVal hwnd As LongPtr) As Long
    Declare PtrSafe Function EmptyClipboard Lib "user32" () As Long
    Declare PtrSafe Function SetClipboardData Lib "user32" (ByVal wFormat As Long, ByVal hMem As LongPtr) As LongPtr
    Declare PtrSafe Function lstrcpy Lib "kernel32" Alias "lstrcpyA" (ByVal lpString1 As Any, ByVal lpString2 As Any) As LongPtr
    Public Const GHND = &H42
    Public Const CF_TEXT = 1
#Else
    Declare Function GlobalUnlock Lib "kernel32" (ByVal hMem As Long) As Long
    Declare Function GlobalLock Lib "kernel32" (ByVal hMem As Long) As Long
    Declare Function GlobalAlloc Lib "kernel32" (ByVal wFlags As Long, ByVal dwBytes As Long) As Long
    Declare Function CloseClipboard Lib "user32" () As Long
    Declare Function OpenClipboard Lib "user32" (ByVal hwnd As Long) As Long
    Declare Function EmptyClipboard Lib "user32" () As Long
    Declare Function SetClipboardData Lib "user32" (ByVal wFormat As Long, ByVal hMem As Long) As Long
    Declare Function lstrcpy Lib "kernel32" Alias "lstrcpyA" (ByVal lpString1 As Any, ByVal lpString2 As Any) As Long
    Public Const GHND = &H42
    Public Const CF_TEXT = 1
#End If

Sub CopyTextToClipboard(sText As String)
    Dim hGlobalMemory As LongPtr, lpGlobalMemory As LongPtr

    ' Allocate moveable global memory
    hGlobalMemory = GlobalAlloc(GHND, Len(sText) + 1)

    ' Lock the block to get a far pointer to this memory
    lpGlobalMemory = GlobalLock(hGlobalMemory)

    ' Copy the string to this global memory
    lpGlobalMemory = lstrcpy(lpGlobalMemory, sText)

    ' Unlock the memory
    If GlobalUnlock(hGlobalMemory) <> 0 Then
        MsgBox "Could not unlock memory location. Copy aborted."
        Exit Sub
    End If

    ' Open Clipboard to copy data to
    If OpenClipboard(0&) = 0 Then
        MsgBox "Could not open the Clipboard. Copy aborted."
        Exit Sub
    End If

    ' Clear the Clipboard
    Call EmptyClipboard

    ' Copy the data to the Clipboard
    hClipMemory = SetClipboardData(CF_TEXT, hGlobalMemory)

    Call CloseClipboard
End Sub
Function GetNewBlockNameFromCSV(ByVal blockNameToFind As String) As String
    Dim csvFilePath As String
    csvFilePath = "C:\Users\ACER\Documents\ACADE_VBA\OldAndNewBlocks.csv" ' Update with the path to your CSV file
    
    Dim fileNo As Integer: fileNo = FreeFile
    Open csvFilePath For Input As #fileNo

    Dim line As String, data As Variant
    Dim newBlockName As String: newBlockName = ""

    ' Read CSV and find matching block name
    Do While Not EOF(fileNo)
        Line Input #fileNo, line
        data = Split(line, ",")

        If UBound(data) >= 3 Then
            If data(0) = blockNameToFind Then
                newBlockName = data(2)
                Exit Do
            End If
        End If
    Loop

    Close #fileNo

    GetNewBlockNameFromCSV = newBlockName
End Function

Sub CopyNewBlockNameToClipboard()
    ' Prompt user to select a block in AutoCAD
    Dim objAcadEntity As AcadEntity
    Dim objPnt As Variant
    On Error Resume Next
    ThisDrawing.Utility.GetEntity objAcadEntity, objPnt, "Select a block:"
    If Err Then
        MsgBox "Error selecting block: " & Err.Description
        Exit Sub
    End If
    On Error GoTo 0
    
    If Not (TypeOf objAcadEntity Is AcadBlockReference) Then
        MsgBox "The Object is Not a Block"
        Exit Sub
    End If
    
    Dim blockNameToFind As String
    blockNameToFind = objAcadEntity.name

    ' Call function to find matching block name
    Dim newBlockName As String
    newBlockName = GetNewBlockNameFromCSV(blockNameToFind)

    ' Copy new block name to clipboard if found
    If newBlockName <> "" Then
        CopyTextToClipboard newBlockName
        ThisDrawing.Utility.Prompt "New Block Name copied to clipboard: " & newBlockName
    Else
        ThisDrawing.Utility.Prompt blockNameToFind & " Not found in CSV."
    End If
End Sub

Sub ReplaceNewBlock()
    ' Prompt user to select a block in AutoCAD
    Dim objAcadEntity As AcadEntity
    Dim objPnt As Variant
    On Error Resume Next
    ThisDrawing.Utility.GetEntity objAcadEntity, objPnt, "Select a block:"
    If Err Then
        MsgBox "Error selecting block: " & Err.Description
        Exit Sub
    End If
    On Error GoTo 0

    If Not (TypeOf objAcadEntity Is AcadBlockReference) Then
        MsgBox "The Object is Not a Block"
        Exit Sub
    End If

    Dim blockNameToFind As String
    blockNameToFind = objAcadEntity.name

    ' Call function to find matching block name
    Dim newBlockName As String
    newBlockName = GetNewBlockNameFromCSV(blockNameToFind)

    ' Copy new block name to clipboard if found
    If newBlockName <> "" Then
        ThisDrawing.SendCommand "bswap_aut" & vbCr & blockNameToFind & vbCr & newBlockName & vbCr
        ThisDrawing.Utility.Prompt blockNameToFind & " is Replaced by " & newBlockName
    Else
        ThisDrawing.Utility.Prompt blockNameToFind & " Not found in CSV."
    End If
End Sub

Sub ShowBlockListForm()
    frmBlockList.show
End Sub

Sub ShowNewWireLayersForm()
    frmNewWireLayers.show
End Sub

Sub ShowChangeFontsForm()
    frmChangeBlockFont.show
End Sub
    
Sub ShowReplaceTagForm()
    frmReplaceTagCSV.show
End Sub

Sub ShowCountEqForm()
    frmCountEq.show
End Sub

Sub ShowReplaceTagManual()
    frmReplaceTag.show
End Sub

Sub showPLCDesc()
    frmPLCDesc.show
End Sub

Sub RefreshTableValues()
    ' This example adds a table in model space and sets and gets a column name
    Dim MyModelSpace As AcadModelSpace
    Set MyModelSpace = ThisDrawing.ModelSpace
    Dim MyTable As AcadTable
    Dim CellVal As Variant
    Dim CellContent As String
    Dim RowCount, TargetCol, i As Integer
    Dim parts() As String
    ' Select a table
    Dim pickedEntity As AcadEntity
    Dim pickedPoint As Variant
    ThisDrawing.Utility.GetEntity pickedEntity, pickedPoint
    If TypeOf pickedEntity Is AcadTable Then
        Set MyTable = pickedEntity
    Else
        MsgBox "You did not select a table."
        Exit Sub
    End If
    TargetCol = val(InputBox("Please Enter the Target Column", "Target Column"))
    If TargetCol = 0 Then
        MsgBox "Input Invalid"
        Exit Sub
    End If
    RowCount = MyTable.Rows
    For i = 2 To RowCount
        CellVal = MyTable.GetCellValue(i, TargetCol)
        If CellVal <> "" Then
            parts = Split(CellVal, ";")
            CellContent = parts(UBound(parts))
            CellContent = replace(CellContent, "}", "")
            Call MyTable.SetCellValue(i, TargetCol, CellContent)
            'Call MyTable.SetCellValueFromText(6, 1, CellContent, acSetDefaultFormat)
            ThisDrawing.Utility.Prompt "Row " & i & vbCrLf
        End If
    Next i
    ThisDrawing.Utility.Prompt "Table Refresh Complete !" & vbCrLf
End Sub

Attribute VB_Name = "frmBlockList"
Attribute VB_Base = "0{B1A17063-F45D-43D3-9CDA-C9A5C633807B}{9EB3FC67-8F04-48A5-91DB-A21A4979C359}"
Attribute VB_GlobalNameSpace = False
Attribute VB_Creatable = False
Attribute VB_PredeclaredId = True
Attribute VB_Exposed = False
Attribute VB_TemplateDerived = False
Attribute VB_Customizable = False
Private Sub lstBlocks_Click()
    Dim selectedBlockName As String
    selectedBlockName = Me.lstBlocks.Value
    ThisDrawing.SendCommand "SelectBlocksByName" & vbCr & selectedBlockName & vbCr
End Sub

Private Sub lstBlocks_DblClick(ByVal Cancel As MSForms.ReturnBoolean)
    Dim selectedBlockName As String
    selectedBlockName = Me.lstBlocks.Value
    ThisDrawing.SendCommand "ZoomToBlockByName" & vbCr & selectedBlockName & vbCr
End Sub

Private Sub UserForm_Initialize()
    Dim doc As AcadDocument
    Set doc = ThisDrawing

    Dim entity As AcadEntity
    Dim blockRef As AcadBlockReference
    Dim insertedBlockNames As New Collection
    Dim name As Variant

    On Error Resume Next ' Ignore errors in the collection (duplicates)
    For Each entity In doc.ModelSpace
        If TypeOf entity Is AcadBlockReference Then
            Set blockRef = entity
            insertedBlockNames.Add blockRef.name, blockRef.name ' Use block name as the key to avoid duplicates
        End If
    Next entity
    On Error GoTo 0 ' Reset error handling

    For Each name In insertedBlockNames
        Me.lstBlocks.AddItem name
    Next name
End Sub

Attribute VB_Name = "frmChangeBlockFont"
Attribute VB_Base = "0{CF599710-1B1A-43B2-8C1D-28DD8B63875A}{82FF9B0C-3614-436E-B8B7-5E8DA54D4AFC}"
Attribute VB_GlobalNameSpace = False
Attribute VB_Creatable = False
Attribute VB_PredeclaredId = True
Attribute VB_Exposed = False
Attribute VB_TemplateDerived = False
Attribute VB_Customizable = False
Private Sub cmdFontBlock_Click()
 If cmbFonts.Text <> "" Then
    ThisDrawing.SendCommand ("ChangeBlocksFont" & vbCr & cmbFonts.Text & vbCr)
 End If
End Sub

Private Sub cmdMleader_Click()
 If cmbFonts.Text <> "" Then
    ThisDrawing.SendCommand ("ChangeMLeaderFont" & vbCr & cmbFonts.Text & vbCr)
 End If
End Sub

Private Sub cmdText_Click()
 If cmbFonts.Text <> "" Then
    ThisDrawing.SendCommand ("ChangeTextFont" & vbCr & cmbFonts.Text & vbCr)
 End If
End Sub

Private Sub UserForm_Initialize()
    Dim i As Integer
    Dim textStyle As AcadTextStyle
    cmbFonts.Clear
    For Each textStyle In ThisDrawing.TextStyles
        cmbFonts.AddItem (textStyle.name)
    Next textStyle
End Sub

Attribute VB_Name = "frmCountEq"
Attribute VB_Base = "0{02BCA80E-39FF-47DD-86EE-3A3ED88060B0}{04261E33-D7DC-4967-8B1F-3B9FA0EB1F7F}"
Attribute VB_GlobalNameSpace = False
Attribute VB_Creatable = False
Attribute VB_PredeclaredId = True
Attribute VB_Exposed = False
Attribute VB_TemplateDerived = False
Attribute VB_Customizable = False
Private Sub cmdCount_Click()
    Dim i As Integer
    Dim result As Variant
    Dim csvFilePath As String
    Dim fileNo As Integer
    Dim length As Integer
    
    length = txtcount.Value

    ' Define the path for the CSV file
    csvFilePath = "C:\Users\ACER\Documents\Results.csv" ' Change this path as needed

    ' Open the CSV file for writing
    fileNo = FreeFile()
    Open csvFilePath For Output As #fileNo

    ' Loop through numbers 1 to 100
    For i = 1 To length
        ' Call the AutoLISP function with the current number as a string
        ' Note: Ensure that the function name matches what you've defined in AutoLISP
        ' and that it's already loaded into the AutoCAD session
        ThisDrawing.SendCommand ("FindMLeaderWithText" & vbCr & CStr(i) & vbCr)
        ' Retrieve the result stored in the USERI1 variable
        result = ThisDrawing.GetVariable("USERI1")

        ' Write the result to the CSV file
        If result = 0 Then
            Print #fileNo, i
        Else
            Print #fileNo, i & "," & result
        End If
    Next i

    ' Close the CSV file
    Close #fileNo

    MsgBox "Results saved to " & csvFilePath
End Sub

Attribute VB_Name = "frmNewWireLayers"
Attribute VB_Base = "0{7B88A47F-F880-4127-97ED-6681D81E2828}{0852623B-4C6A-4519-BA21-D56774D18302}"
Attribute VB_GlobalNameSpace = False
Attribute VB_Creatable = False
Attribute VB_PredeclaredId = True
Attribute VB_Exposed = False
Attribute VB_TemplateDerived = False
Attribute VB_Customizable = False
Private Sub cmdOther_Click()
    ThisDrawing.SendCommand ("CreateNewWireLayerNoNum" & vbCr & "CTRL_NO_NUMBER" & vbCr)
    ThisDrawing.SendCommand ("CreateNewWireLayer" & vbCr & "CTRL_NUMBERED" & vbCr)
End Sub



Private Sub cmdProcess_Click()
    Dim startVal, endVal, prefix, layerName As String
    Dim numDigits, startNum, endNum, i As Integer
    startVal = txtFrom.Text
    endVal = txtTo.Text
    prefix = txtPrefix.Text
    If Not (IsNumeric(startVal) And IsNumeric(endVal)) Then
        MsgBox "Please enter a valid number."
        Exit Sub
    End If
    numDigits = Len(startVal)
    startNum = CInt(startVal)
    endNum = CInt(endVal)
    For i = startNum To endNum
        layerName = prefix & Format(i, String(numDigits, "0"))
        ThisDrawing.SendCommand ("CreateNewWireLayer" & vbCr & layerName & vbCr)
        ThisDrawing.Utility.Prompt ("Layer " & layerName & " Created" & vbCrLf)
        Sleep 20
    Next i
End Sub

Attribute VB_Name = "frmPLCDesc"
Attribute VB_Base = "0{650F3079-3343-49D3-A71E-79E9769262FF}{19163D41-7B26-46F1-9490-39335BC66C1B}"
Attribute VB_GlobalNameSpace = False
Attribute VB_Creatable = False
Attribute VB_PredeclaredId = True
Attribute VB_Exposed = False
Attribute VB_TemplateDerived = False
Attribute VB_Customizable = False
Dim terminal As Integer
Dim PLCDesc As Collection
Dim skipTerm() As Integer
Sub Terminal_UP()
    Dim item As Variant
    terminal = val(txtTerm.Text)
    terminal = terminal + 1
    For Each item In skipTerm
    If terminal = item Then
        terminal = terminal + 1
    End If
    Next item
    txtTerm.Text = Format$(terminal, "00")
End Sub
Sub Terminal_Down()
    Dim item As Variant
    terminal = val(txtTerm.Text)
    If terminal = 0 Then
        Exit Sub
    End If
    terminal = terminal - 1
    For Each item In skipTerm
    If terminal = item Then
        terminal = terminal - 1
    End If
    Next item
    txtTerm.Text = Format$(terminal, "00")
End Sub
Sub Terminal_Load()
    terminal = val(txtTerm.Text)
    txtTerm.Text = Format$(terminal, "00")
End Sub

Private Sub cmdClear_Click()
    Terminal_Load
    ThisDrawing.SendCommand "ChangeAttrValByType" & vbCr & "" & vbCr & 1 & vbCr & "DESCA" & Format$(terminal, "00") & vbCr
    ThisDrawing.SendCommand "ChangeAttrValByType" & vbCr & "" & vbCr & 1 & vbCr & "DESCB" & Format$(terminal, "00") & vbCr
    ThisDrawing.SendCommand "ChangeAttrValByType" & vbCr & "" & vbCr & 1 & vbCr & "DESCC" & Format$(terminal, "00") & vbCr
    ThisDrawing.SendCommand "ChangeAttrValByType" & vbCr & "" & vbCr & 1 & vbCr & "DESCD" & Format$(terminal, "00") & vbCr
End Sub

Private Sub cmdDown_Click()
    Terminal_Down
End Sub

Private Sub cmdInsert_Click()
    Dim e As Variant
    Dim i As Integer
    Terminal_Load
    For Each e In PLCDesc
        If e(0) = cmbType.Text Then
            ThisDrawing.SendCommand "ChangeAttrValByType" & vbCr & """" & txtDesc.Text & """" & vbCr & 1 & vbCr & "DESCA" & Format$(terminal, "00") & vbCr
            ThisDrawing.SendCommand "ChangeAttrValByType" & vbCr & """" & e(2) & """" & vbCr & 1 & vbCr & "DESCB" & Format$(terminal, "00") & vbCr
            ThisDrawing.SendCommand "ChangeAttrValByType" & vbCr & """" & e(3) & """" & vbCr & 1 & vbCr & "DESCC" & Format$(terminal, "00") & vbCr
            Terminal_UP
        End If
    Next e
End Sub

Private Sub cmdSet_Click()
Dim counter As Integer
    InitSkip
End Sub

Private Sub cmdTxtxInsert_Click()
    Terminal_Load
    ThisDrawing.SendCommand "ChangeAttrValByType" & vbCr & """" & txtDesc.Text & """" & vbCr & 1 & vbCr & "DESCA" & Format$(terminal, "00") & vbCr
    ThisDrawing.SendCommand "ChangeAttrValByType" & vbCr & """" & txtDescB.Text & """" & vbCr & 1 & vbCr & "DESCB" & Format$(terminal, "00") & vbCr
    ThisDrawing.SendCommand "ChangeAttrValByType" & vbCr & """" & txtDescC.Text & """" & vbCr & 1 & vbCr & "DESCC" & Format$(terminal, "00") & vbCr
    Terminal_UP
End Sub

Private Sub cmdUP_Click()
    Terminal_UP
End Sub

Sub InitSkip()
    Dim values() As String
    Dim i As Integer
    values = Split(txtSkip.Text, ",")
    ReDim skipTerm(0 To UBound(values))
    For i = LBound(values) To UBound(values)
        skipTerm(i) = CInt(values(i))
    Next i
End Sub

Private Sub UserForm_Initialize()
Dim csvPath As String
Dim csvData As String
Dim parts() As String
InitSkip
Terminal_Load
    With cmbType
        .AddItem "DEFAULT"
        .AddItem "DEVICE"
        .AddItem "VSD"
        .AddItem "DOL"
        .AddItem "TS"
    End With
' Initialize the FindReplaceList collection
Set PLCDesc = New Collection
csvPath = "C:\Users\ACER\Documents\ACADE_VBA\PLCDef.csv"
Open csvPath For Input As #1
Do Until EOF(1)
    Line Input #1, csvData ' Read each line from the file
    parts = Split(csvData, ",") ' Split the line into parts using the comma as a delimiter
    If UBound(parts) >= 2 Then
        PLCDesc.Add Array(parts(0), parts(1), parts(2), parts(3)) ' Add the pair to the list
    End If
Loop
Close #1
End Sub

Attribute VB_Name = "frmReplaceTag"
Attribute VB_Base = "0{D3CD47A6-1A6B-4C24-AE8C-A5FADB061A3E}{5832780D-E903-48CC-B051-10EAD3EA30F8}"
Attribute VB_GlobalNameSpace = False
Attribute VB_Creatable = False
Attribute VB_PredeclaredId = True
Attribute VB_Exposed = False
Attribute VB_TemplateDerived = False
Attribute VB_Customizable = False


Private Sub cmdChangePLC_Click()
Dim find, replace, blockType, Attr As String
find = txtFind.Text
replace = txtReplace.Text
blockType = "1"
Attr = cmbPlcAttr.Text & txtNum.Text
ThisDrawing.SendCommand ("ReplaceAttrValByType" & vbCr & """" & find & """" & vbCr & """" & replace & """" & vbCr & blockType & vbCr & Attr & vbCr)
End Sub

Private Sub cmdReplace_Click()
Dim find, replace As String
find = txtFind.Text
replace = txtReplace.Text
ThisDrawing.SendCommand ("ReplaceTagValContd" & vbCr & """" & find & """" & vbCr & """" & replace & """" & vbCr)
End Sub

Private Sub cmdSelectAttr_Click()
Dim find, replace, blockType, Attr As String
find = txtFind.Text
replace = txtReplace.Text
Attr = cmbAttrname.Text
ThisDrawing.SendCommand ("ReplaceAttrValContd" & vbCr & """" & find & """" & vbCr & """" & replace & """" & vbCr & Attr & vbCr)
End Sub

Private Sub cmdText_Click()
Dim find, replace, blockType As String
find = txtFind.Text
replace = txtReplace.Text
ThisDrawing.SendCommand ("FindReplaceTextMTextContd" & vbCr & """" & find & """" & vbCr & """" & replace & """" & vbCr)
End Sub
Private Sub spn1_Change()
     txtNum.Text = Format$(spn1.Value, "00")
End Sub

Private Sub txtNum_Exit(ByVal Cancel As MSForms.ReturnBoolean)
    spn1.Value = txtNum.Value
End Sub

Private Sub UserForm_Initialize()
    With Me.cmbAttrname
        .AddItem "DESC1"
        .AddItem "DESC2"
        .AddItem "DESC3"
        .AddItem "LOC"
    End With
    With Me.cmbPlcAttr
        .AddItem "DESCA"
        .AddItem "DESCB"
        .AddItem "DESCC"
    End With
End Sub

Attribute VB_Name = "frmReplaceTagCSV"
Attribute VB_Base = "0{A84A0E1C-5D88-466A-BFD5-6BD817368E15}{D0753D85-FA00-416D-A743-B390B5D858D0}"
Attribute VB_GlobalNameSpace = False
Attribute VB_Creatable = False
Attribute VB_PredeclaredId = True
Attribute VB_Exposed = False
Attribute VB_TemplateDerived = False
Attribute VB_Customizable = False
' Global variable to store find/replace pairs
Dim FindReplaceList As Collection
Private Sub cmdLoadCSV_Click()
Dim csvPath As String
Dim csvData As String
Dim parts() As String
ThisDrawing.SendCommand "GetCSVFilePath" & vbCr
csvPath = ThisDrawing.GetVariable("USERS1")
' Check if a CSV file path was actually retrieved
If csvPath = "" Then
    MsgBox "No CSV file selected.", vbExclamation
    Exit Sub
End If

' Initialize the FindReplaceList collection
Set FindReplaceList = New Collection
lstFindTags.Clear
' Open the CSV file and read its contents
Open csvPath For Input As #1
Do Until EOF(1)
    Line Input #1, csvData ' Read each line from the file
    parts = Split(csvData, ",") ' Split the line into parts using the comma as a delimiter
    
    ' Ensure there are at least two parts (find text and replace text)
    If UBound(parts) >= 1 Then
        FindReplaceList.Add Array(parts(0), parts(1)) ' Add the pair to the list
        lstFindTags.AddItem parts(0)
    End If
Loop
Close #1
End Sub
Private Sub cmdChild_Click()
Dim find, replace, blockType As String
find = txtFind.Text
replace = txtReplace.Text
blockType = "5"
ThisDrawing.SendCommand ("ReplaceTagValByType" & vbCr & """" & find & """" & vbCr & """" & replace & """" & vbCr & blockType & vbCr)
End Sub

Private Sub cmdDesc1_Click()
Dim find, replace, blockType As String
find = txtFind.Text
replace = txtReplace.Text
ThisDrawing.SendCommand ("ReplaceAttrVal" & vbCr & """" & find & """" & vbCr & """" & replace & """" & vbCr & "DESC1" & vbCr)
End Sub

Private Sub cmdDesc2_Click()
Dim find, replace, blockType As String
find = txtFind.Text
replace = txtReplace.Text
ThisDrawing.SendCommand ("ReplaceAttrVal" & vbCr & """" & find & """" & vbCr & """" & replace & """" & vbCr & "DESC2" & vbCr)
End Sub

Private Sub cmdDesc3_Click()
Dim find, replace, blockType As String
find = txtFind.Text
replace = txtReplace.Text
ThisDrawing.SendCommand ("ReplaceAttrVal" & vbCr & """" & find & """" & vbCr & """" & replace & """" & vbCr & "DESC3" & vbCr)
End Sub

Private Sub cmdPar_Click()
Dim find, replace, blockType As String
find = txtFind.Text
replace = txtReplace.Text
blockType = "4"
ThisDrawing.SendCommand ("ReplaceTagValByType" & vbCr & """" & find & """" & vbCr & """" & replace & """" & vbCr & blockType & vbCr)
End Sub

Private Sub cmdReplace_Click()
Dim find, replace As String
find = txtFind.Text
replace = txtReplace.Text
ThisDrawing.SendCommand ("ReplaceTagVal" & vbCr & find & vbCr & replace & vbCr)
End Sub
Private Sub cmdplc_Click()
Dim find, replace, blockType As String
find = txtFind.Text
replace = txtReplace.Text
blockType = "1"
ThisDrawing.SendCommand ("ReplaceTagValByType" & vbCr & """" & find & """" & vbCr & """" & replace & """" & vbCr & blockType & vbCr)
End Sub

Private Sub cmdplcdescA_Click()
Dim find, replace, blockType, numAttr As String
find = txtFind.Text
replace = txtReplace.Text
numAttr = txtnumPlcAttr.Text
blockType = "1"
ThisDrawing.SendCommand ("ReplaceMultipleAttrValsByType" & vbCr & """" & find & """" & vbCr & """" & replace & """" & vbCr & blockType & vbCr & "DESCA" & vbCr & numAttr & vbCr)
End Sub

Private Sub cmdplcsedcB_Click()
Dim find, replace, blockType, numAttr As String
find = txtFind.Text
replace = txtReplace.Text
numAttr = txtnumPlcAttr.Text
blockType = "1"
ThisDrawing.SendCommand ("ReplaceMultipleAttrValsByType" & vbCr & """" & find & """" & vbCr & """" & replace & """" & vbCr & blockType & vbCr & "DESCB" & vbCr & numAttr & vbCr)
End Sub

Private Sub cmdPtag_Click()
Dim find, replace, blockType As String
find = txtFind.Text
replace = txtReplace.Text
ThisDrawing.SendCommand ("ReplaceAttrVal" & vbCr & """" & find & """" & vbCr & """" & replace & """" & vbCr & "P_TAG1" & vbCr)
End Sub

Private Sub cmdTerm_Click()
Dim find, replace, blockType As String
find = txtFind.Text
replace = txtReplace.Text
blockType = "7"
ThisDrawing.SendCommand ("ReplaceTagValByType" & vbCr & """" & find & """" & vbCr & """" & replace & """" & vbCr & blockType & vbCr)
End Sub

Private Sub cmdTermLoc_Click()
Dim find, replace, blockType As String
find = txtFind.Text
replace = txtReplace.Text
blockType = "7"
ThisDrawing.SendCommand ("ReplaceAttrValByType" & vbCr & """" & find & """" & vbCr & """" & replace & """" & vbCr & blockType & vbCr & "LOC" & vbCr)
End Sub

Private Sub cmdText_Click()
Dim find, replace, blockType As String
find = txtFind.Text
replace = txtReplace.Text
ThisDrawing.SendCommand ("FindReplaceTextMText" & vbCr & """" & find & """" & vbCr & """" & replace & """" & vbCr)
End Sub

Private Sub cmdWireno_Click()
Dim find, replace, blockType As String
find = txtFind.Text
replace = txtReplace.Text
blockType = "2"
ThisDrawing.SendCommand ("ReplaceAttrValByType" & vbCr & """" & find & """" & vbCr & """" & replace & """" & vbCr & blockType & vbCr & "WIRENO" & vbCr)
End Sub

Private Sub cmdWireNoFix_Click()
Dim find, replace, blockType As String
find = txtFind.Text
replace = txtReplace.Text
blockType = "2"
ThisDrawing.SendCommand ("ReplaceAttrValByType" & vbCr & """" & find & """" & vbCr & """" & replace & """" & vbCr & blockType & vbCr & "WIRENOF" & vbCr)
End Sub


Private Sub lstFindTags_Click()
txtFind.Text = lstFindTags.Value
txtReplace.Text = FindReplaceList.item(lstFindTags.ListIndex + 1)(1)
End Sub

Private Sub UserForm_Initialize()
Set FindReplaceList = New Collection
End Sub

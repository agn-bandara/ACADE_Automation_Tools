Attribute VB_Name = "Module1"
#If VBA7 Then
    Declare PtrSafe Function GlobalUnlock Lib "kernel32" (ByVal hMem As LongPtr) As Long
    Declare PtrSafe Function GlobalLock Lib "kernel32" (ByVal hMem As LongPtr) As LongPtr
    Declare PtrSafe Function GlobalAlloc Lib "kernel32" (ByVal wFlags As Long, ByVal dwBytes As Long) As LongPtr
    Declare PtrSafe Function CloseClipboard Lib "user32" () As Long
    Declare PtrSafe Function OpenClipboard Lib "user32" (ByVal hwnd As LongPtr) As Long
    Declare PtrSafe Function EmptyClipboard Lib "user32" () As Long
    Declare PtrSafe Function SetClipboardData Lib "user32" (ByVal wFormat As Long, ByVal hMem As LongPtr) As LongPtr
    Declare PtrSafe Function lstrcpy Lib "kernel32" Alias "lstrcpyA" (ByVal lpString1 As Any, ByVal lpString2 As Any) As LongPtr
    Public Const GHND = &H42
    Public Const CF_TEXT = 1
#Else
    Declare Function GlobalUnlock Lib "kernel32" (ByVal hMem As Long) As Long
    Declare Function GlobalLock Lib "kernel32" (ByVal hMem As Long) As Long
    Declare Function GlobalAlloc Lib "kernel32" (ByVal wFlags As Long, ByVal dwBytes As Long) As Long
    Declare Function CloseClipboard Lib "user32" () As Long
    Declare Function OpenClipboard Lib "user32" (ByVal hwnd As Long) As Long
    Declare Function EmptyClipboard Lib "user32" () As Long
    Declare Function SetClipboardData Lib "user32" (ByVal wFormat As Long, ByVal hMem As Long) As Long
    Declare Function lstrcpy Lib "kernel32" Alias "lstrcpyA" (ByVal lpString1 As Any, ByVal lpString2 As Any) As Long
    Public Const GHND = &H42
    Public Const CF_TEXT = 1
#End If

Sub CopyTextToClipboard(sText As String)
    Dim hGlobalMemory As LongPtr, lpGlobalMemory As LongPtr

    ' Allocate moveable global memory
    hGlobalMemory = GlobalAlloc(GHND, Len(sText) + 1)

    ' Lock the block to get a far pointer to this memory
    lpGlobalMemory = GlobalLock(hGlobalMemory)

    ' Copy the string to this global memory
    lpGlobalMemory = lstrcpy(lpGlobalMemory, sText)

    ' Unlock the memory
    If GlobalUnlock(hGlobalMemory) <> 0 Then
        MsgBox "Could not unlock memory location. Copy aborted."
        Exit Sub
    End If

    ' Open Clipboard to copy data to
    If OpenClipboard(0&) = 0 Then
        MsgBox "Could not open the Clipboard. Copy aborted."
        Exit Sub
    End If

    ' Clear the Clipboard
    Call EmptyClipboard

    ' Copy the data to the Clipboard
    hClipMemory = SetClipboardData(CF_TEXT, hGlobalMemory)

    Call CloseClipboard
End Sub
Sub CopyNewBlockNameToClipboard()
    Dim csvFilePath As String
    csvFilePath = "C:\Users\ACER\Documents\ACADE_VBA\OldAndNewBlocks.csv" ' Update with the path to your CSV file

    Dim fileNo As Integer: fileNo = FreeFile
    Open csvFilePath For Input As #fileNo

    Dim line As String, data As Variant
    Dim blockNameToFind As String, found As Boolean: found = False
    Dim newBlockName As String

    ' Prompt user to select a block in AutoCAD
    Dim objAcadEntity As AcadEntity
    Dim objPnt As Variant
    On Error Resume Next
    ThisDrawing.Utility.GetEntity objAcadEntity, objPnt, "Select a block:"
    If Err Then
        MsgBox "Error selecting block: " & Err.Description
        Close #fileNo
        Exit Sub
    End If
    On Error GoTo 0
    blockNameToFind = objAcadEntity.name

    ' Read CSV and find matching block name
    Do While Not EOF(fileNo)
        Line Input #fileNo, line
        data = Split(line, ",")

        If UBound(data) >= 3 Then
            If data(0) = blockNameToFind Then
                newBlockName = data(2)
                found = True
                Exit Do
            End If
        End If
    Loop

    Close #fileNo

    ' Copy new block name to clipboard if found
    If found Then
        CopyTextToClipboard newBlockName
        MsgBox "New Block Name copied to clipboard: " & newBlockName
    Else
        MsgBox "Matching block name not found in CSV."
    End If
End Sub

Sub ShowBlockListForm()
    frmBlockList.show
End Sub

Attribute VB_Name = "frmBlockList"
Attribute VB_Base = "0{8358DF46-3CDE-4762-A968-2FA04A6FCF84}{FDC7A0E0-E668-4B89-998D-62A8CBFB7B26}"
Attribute VB_GlobalNameSpace = False
Attribute VB_Creatable = False
Attribute VB_PredeclaredId = True
Attribute VB_Exposed = False
Attribute VB_TemplateDerived = False
Attribute VB_Customizable = False
Private Sub lstBlocks_Click()
    Dim selectedBlockName As String
    selectedBlockName = Me.lstBlocks.Value
    ThisDrawing.SendCommand "SelectBlocksByName" & vbCr & selectedBlockName & vbCr
End Sub

Private Sub lstBlocks_DblClick(ByVal Cancel As MSForms.ReturnBoolean)
    Dim selectedBlockName As String
    selectedBlockName = Me.lstBlocks.Value
    ThisDrawing.SendCommand "ZoomToBlockByName" & vbCr & selectedBlockName & vbCr
End Sub

Private Sub UserForm_Initialize()
    Dim doc As AcadDocument
    Set doc = ThisDrawing

    Dim entity As AcadEntity
    Dim blockRef As AcadBlockReference
    Dim insertedBlockNames As New Collection
    Dim name As Variant

    On Error Resume Next ' Ignore errors in the collection (duplicates)
    For Each entity In doc.ModelSpace
        If TypeOf entity Is AcadBlockReference Then
            Set blockRef = entity
            insertedBlockNames.Add blockRef.name, blockRef.name ' Use block name as the key to avoid duplicates
        End If
    Next entity
    On Error GoTo 0 ' Reset error handling

    For Each name In insertedBlockNames
        Me.lstBlocks.AddItem name
    Next name
End Sub

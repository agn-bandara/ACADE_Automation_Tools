Attribute VB_Name = "Module1"
Declare PtrSafe Sub Sleep Lib "kernel32" (ByVal dwMilliseconds As Long)
#If VBA7 Then
    Declare PtrSafe Function GlobalUnlock Lib "kernel32" (ByVal hMem As LongPtr) As Long
    Declare PtrSafe Function GlobalLock Lib "kernel32" (ByVal hMem As LongPtr) As LongPtr
    Declare PtrSafe Function GlobalAlloc Lib "kernel32" (ByVal wFlags As Long, ByVal dwBytes As Long) As LongPtr
    Declare PtrSafe Function CloseClipboard Lib "user32" () As Long
    Declare PtrSafe Function OpenClipboard Lib "user32" (ByVal hWnd As LongPtr) As Long
    Declare PtrSafe Function EmptyClipboard Lib "user32" () As Long
    Declare PtrSafe Function SetClipboardData Lib "user32" (ByVal wFormat As Long, ByVal hMem As LongPtr) As LongPtr
    Declare PtrSafe Function lstrcpy Lib "kernel32" Alias "lstrcpyA" (ByVal lpString1 As Any, ByVal lpString2 As Any) As LongPtr
    Public Const GHND = &H42
    Public Const CF_TEXT = 1
#Else
    Declare Function GlobalUnlock Lib "kernel32" (ByVal hMem As Long) As Long
    Declare Function GlobalLock Lib "kernel32" (ByVal hMem As Long) As Long
    Declare Function GlobalAlloc Lib "kernel32" (ByVal wFlags As Long, ByVal dwBytes As Long) As Long
    Declare Function CloseClipboard Lib "user32" () As Long
    Declare Function OpenClipboard Lib "user32" (ByVal hwnd As Long) As Long
    Declare Function EmptyClipboard Lib "user32" () As Long
    Declare Function SetClipboardData Lib "user32" (ByVal wFormat As Long, ByVal hMem As Long) As Long
    Declare Function lstrcpy Lib "kernel32" Alias "lstrcpyA" (ByVal lpString1 As Any, ByVal lpString2 As Any) As Long
    Public Const GHND = &H42
    Public Const CF_TEXT = 1
#End If

Sub CopyTextToClipboard(sText As String)
    Dim hGlobalMemory As LongPtr, lpGlobalMemory As LongPtr

    ' Allocate moveable global memory
    hGlobalMemory = GlobalAlloc(GHND, Len(sText) + 1)

    ' Lock the block to get a far pointer to this memory
    lpGlobalMemory = GlobalLock(hGlobalMemory)

    ' Copy the string to this global memory
    lpGlobalMemory = lstrcpy(lpGlobalMemory, sText)

    ' Unlock the memory
    If GlobalUnlock(hGlobalMemory) <> 0 Then
        MsgBox "Could not unlock memory location. Copy aborted."
        Exit Sub
    End If

    ' Open Clipboard to copy data to
    If OpenClipboard(0&) = 0 Then
        MsgBox "Could not open the Clipboard. Copy aborted."
        Exit Sub
    End If

    ' Clear the Clipboard
    Call EmptyClipboard

    ' Copy the data to the Clipboard
    hClipMemory = SetClipboardData(CF_TEXT, hGlobalMemory)

    Call CloseClipboard
End Sub
Function GetNewBlockNameFromCSV(ByVal blockNameToFind As String) As String
    Dim csvFilePath As String
    csvFilePath = "C:\Users\user\Documents\ACADE_VBA\OldAndNewBlocks.csv" ' Update with the path to your CSV file
    
    Dim fileNo As Integer: fileNo = FreeFile
    Open csvFilePath For Input As #fileNo

    Dim line As String, data As Variant
    Dim newBlockName As String: newBlockName = ""

    ' Read CSV and find matching block name
    Do While Not EOF(fileNo)
        Line Input #fileNo, line
        data = Split(line, ",")

        If UBound(data) >= 3 Then
            If data(0) = blockNameToFind Then
                newBlockName = data(2)
                Exit Do
            End If
        End If
    Loop

    Close #fileNo

    GetNewBlockNameFromCSV = newBlockName
End Function

Sub CopyNewBlockNameToClipboard()
    ' Prompt user to select a block in AutoCAD
    Dim objAcadEntity As AcadEntity
    Dim objPnt As Variant
    On Error Resume Next
    ThisDrawing.Utility.GetEntity objAcadEntity, objPnt, "Select a block:"
    If Err Then
        MsgBox "Error selecting block: " & Err.Description
        Exit Sub
    End If
    On Error GoTo 0
    
    If Not (TypeOf objAcadEntity Is AcadBlockReference) Then
        MsgBox "The Object is Not a Block"
        Exit Sub
    End If
    
    Dim blockNameToFind As String
    blockNameToFind = objAcadEntity.name

    ' Call function to find matching block name
    Dim newBlockName As String
    newBlockName = GetNewBlockNameFromCSV(blockNameToFind)

    ' Copy new block name to clipboard if found
    If newBlockName <> "" Then
        CopyTextToClipboard newBlockName
        ThisDrawing.Utility.Prompt "New Block Name copied to clipboard: " & newBlockName
    Else
        ThisDrawing.Utility.Prompt blockNameToFind & " Not found in CSV."
    End If
End Sub

Sub ReplaceNewBlock()
    ' Prompt user to select a block in AutoCAD
    Dim objAcadEntity As AcadEntity
    Dim objPnt As Variant
    On Error Resume Next
    ThisDrawing.Utility.GetEntity objAcadEntity, objPnt, "Select a block:"
    If Err Then
        MsgBox "Error selecting block: " & Err.Description
        Exit Sub
    End If
    On Error GoTo 0

    If Not (TypeOf objAcadEntity Is AcadBlockReference) Then
        MsgBox "The Object is Not a Block"
        Exit Sub
    End If

    Dim blockNameToFind As String
    blockNameToFind = objAcadEntity.name

    ' Call function to find matching block name
    Dim newBlockName As String
    newBlockName = GetNewBlockNameFromCSV(blockNameToFind)

    ' Copy new block name to clipboard if found
    If newBlockName <> "" Then
        ThisDrawing.SendCommand "bswap_aut" & vbCr & blockNameToFind & vbCr & newBlockName & vbCr
        ThisDrawing.Utility.Prompt blockNameToFind & " is Replaced by " & newBlockName
    Else
        ThisDrawing.Utility.Prompt blockNameToFind & " Not found in CSV."
    End If
End Sub

Sub ShowBlockListForm()
    frmBlockList.show
End Sub

Sub ShowNewWireLayersForm()
    frmNewWireLayers.show
End Sub

Sub ShowChangeFontsForm()
    frmChangeBlockFont.show
End Sub
    
Sub ShowReplaceTagForm()
    frmReplaceTagCSV.show
End Sub

Sub ShowCountEqForm()
    frmCountEq.show
End Sub

Sub ShowReplaceTagManual()
    frmReplaceTag.show
End Sub

Sub showPLCDesc()
    frmPLCDesc.show
End Sub

Sub RefreshTableValues()
    ' This example adds a table in model space and sets and gets a column name
    Dim MyModelSpace As AcadModelSpace
    Set MyModelSpace = ThisDrawing.modelSpace
    Dim MyTable As AcadTable
    Dim CellVal As Variant
    Dim CellContent As String
    Dim rowCount, TargetCol, i As Integer
    Dim parts() As String
    ' Select a table
    Dim pickedEntity As AcadEntity
    Dim pickedPoint As Variant
    ThisDrawing.Utility.GetEntity pickedEntity, pickedPoint
    If TypeOf pickedEntity Is AcadTable Then
        Set MyTable = pickedEntity
    Else
        MsgBox "You did not select a table."
        Exit Sub
    End If
    TargetCol = Val(InputBox("Please Enter the Target Column", "Target Column"))
    'If TargetCol = 0 Then
        'MsgBox "Input Invalid"
        'Exit Sub
    'End If
    rowCount = MyTable.rows
    For i = 2 To rowCount
        CellVal = MyTable.GetCellValue(i, TargetCol)
        If CellVal <> "" Then
            parts = Split(CellVal, ";")
            CellContent = parts(UBound(parts))
            CellContent = replace(CellContent, "}", "")
            Call MyTable.SetCellValue(i, TargetCol, CellContent)
            'Call MyTable.SetCellValueFromText(6, 1, CellContent, acSetDefaultFormat)
            ThisDrawing.Utility.Prompt "Row " & i & vbCrLf
        End If
    Next i
    ThisDrawing.Utility.Prompt "Table Refresh Complete !" & vbCrLf
End Sub

Sub ShowTextMtext()
    frmTextMtext.show
End Sub

Sub ShowInsertTagForm()
    frmInsertTag.show
End Sub

Sub ShowMulticatForm()
    frmMulticat.show
End Sub

Sub ShowPinlistForm()
    frmPinlist.show
End Sub

Sub Sequencer()
    frmSequencer.show
End Sub

Sub CopyDwg()
    frmCopyDwg.show
End Sub

Sub SubsecTag()
    frmSubsecTag.show
End Sub
Sub ItemCount()
    frmItemCount.show
End Sub

Attribute VB_Name = "Module2"
' First, create a new UserForm and name it "ProgressForm"
' Add two Labels to the form:
' 1. Named "lblProgress" for displaying text
' 2. Named "lblProgressBar" for visually representing progress

' ProgressForm code
Private Sub UserForm_Initialize()
    Me.Caption = "Consolidating BOM Table"
    Me.lblProgress.Caption = "Initializing..."
    Me.lblProgressBar.BackColor = RGB(0, 128, 0)  ' Green color
    Me.lblProgressBar.Width = 0
    
    ' Position the progress bar with margins
    Me.lblProgressBar.Left = 10  ' 10 pixels from left
End Sub

' Main module code
Sub ConsolidateBOM()
    On Error GoTo ErrorHandler
    
    Dim acDoc As AcadDocument
    Dim oldTable As AcadTable
    Dim rows As Long, cols As Long
    Dim itemCol As Long, qtyCol As Long, locCol As Long
    Dim locations As New Collection
    Dim items As New Collection
    Dim row As Long, col As Long
    Dim item As Variant, loc As Variant
    Dim qty As Long, total As Long
    Dim hasBlank As Boolean
    Dim progressForm As New progressForm
    
    ' Show progress form
    progressForm.show vbModeless
    UpdateProgress progressForm, "Selecting table...", 0
    
    ' Get the active document
    Set acDoc = ThisDrawing
    
    ' Prompt user to select the table
    Dim pickPoint(0 To 2) As Double
    Dim entityName As AcadEntity
    
    On Error Resume Next
    ThisDrawing.Utility.GetEntity entityName, pickPoint, "Select the BOM table to consolidate: "
    If Err.Number <> 0 Then
        MsgBox "Error selecting entity: " & Err.Description
        Unload progressForm
        Exit Sub
    End If
    On Error GoTo ErrorHandler
    
    If entityName Is Nothing Then
        MsgBox "No entity selected. Exiting macro."
        Unload progressForm
        Exit Sub
    End If
    
    If TypeOf entityName Is AcadTable Then
        Set oldTable = entityName
    Else
        MsgBox "Selected entity is not a table. Exiting macro."
        Unload progressForm
        Exit Sub
    End If
    
    ' Get table dimensions
    rows = oldTable.rows
    cols = oldTable.Columns
    
    UpdateProgress progressForm, "Analyzing table structure...", 10
    
    ' Find ITEM, QTY, and TEMP_LOC columns
    For col = 0 To cols - 1
        Select Case oldTable.GetText(1, col)
            Case "ITEM"
                itemCol = col
            Case "QTY"
                qtyCol = col
            Case "TEMP_LOC"
                locCol = col
        End Select
    Next col
    
    ' Check if all required columns were found
    If itemCol = -1 Or qtyCol = -1 Or locCol = -1 Then
        MsgBox "Could not find ITEM, QTY, or TEMP_LOC columns. Exiting macro."
        Unload progressForm
        Exit Sub
    End If
    
    UpdateProgress progressForm, "Extracting unique items and locations...", 20
    
    ' Extract unique locations and items
    For row = 2 To rows - 1
        item = oldTable.GetText(row, itemCol)
        loc = oldTable.GetText(row, locCol)
        
        If Not ItemExists(items, CStr(item)) Then
            items.Add item, CStr(item)
        End If
        
        If loc <> "" And Not ItemExists(locations, CStr(loc)) Then
            locations.Add loc, CStr(loc)
        ElseIf loc = "" Then
            hasBlank = True
        End If
    Next row
    
    ' Add BLANK to locations if there are blank entries
    If hasBlank Then
        locations.Add "BLANK", "BLANK"
    End If
    
    UpdateProgress progressForm, "Adding new columns...", 30
    
    ' Add new columns
    oldTable.InsertColumns cols, oldTable.GetColumnWidth(qtyCol), locations.Count + 1
    
    ' Add new column headers
    col = cols
    For Each loc In locations
        oldTable.SetText 1, col, CStr(loc)
        col = col + 1
    Next loc
    oldTable.SetText 1, col, "TOTAL"
    
    UpdateProgress progressForm, "Consolidating data...", 40
    
    ' Consolidate data and remove duplicates
    Dim newRow As Long
    newRow = 2
    Dim ItemCount As Long
    ItemCount = items.Count
    Dim currentItem As Long
    currentItem = 0
    
    For Each item In items
        col = cols
        total = 0
        For Each loc In locations
            qty = 0
            For row = 2 To rows - 1
                If oldTable.GetText(row, itemCol) = item Then
                    If (loc = "BLANK" And oldTable.GetText(row, locCol) = "") Or _
                       (oldTable.GetText(row, locCol) = loc) Then
                        qty = qty + CLng(oldTable.GetText(row, qtyCol))
                    End If
                End If
            Next row
            If qty > 0 Then
                oldTable.SetText newRow, col, CStr(qty)
            End If
            total = total + qty
            col = col + 1
        Next loc
        oldTable.SetText newRow, col, CStr(total)
        
        ' Copy original data for this item
        For row = 2 To rows - 1
            If oldTable.GetText(row, itemCol) = item Then
                For col = 0 To cols - 1
                    oldTable.SetText newRow, col, oldTable.GetText(row, col)
                Next col
                Exit For
            End If
        Next row
        
        newRow = newRow + 1
        currentItem = currentItem + 1
        UpdateProgress progressForm, "Consolidating data... " & currentItem & " of " & ItemCount, 40 + (currentItem / ItemCount) * 50
    Next item
    
    UpdateProgress progressForm, "Finalizing table...", 90
    
    ' Resize the table to remove excess rows
    oldTable.DeleteRows newRow, rows - newRow
    
    ' Remove TEMP_LOC and QTY columns after processing
    If locCol > qtyCol Then
        oldTable.DeleteColumns locCol, 1
        oldTable.DeleteColumns qtyCol, 1
    Else
        oldTable.DeleteColumns qtyCol, 1
        oldTable.DeleteColumns locCol, 1
    End If
    
    UpdateProgress progressForm, "Complete!", 100
    
    MsgBox "BOM table consolidated successfully."
    Unload progressForm
    Exit Sub

ErrorHandler:
    MsgBox "An error occurred: " & Err.Description
    Unload progressForm
End Sub

Sub UpdateProgress(form As progressForm, Status As String, percentage As Integer)
    form.lblProgress.Caption = Status
    ' Calculate progress bar width with margins
    ' Using form width minus 20 (10 pixels margin on each side)
    form.lblProgressBar.Width = (form.Width - 20) * (percentage / 100)
    DoEvents
End Sub

Function ItemExists(col As Collection, key As String) As Boolean
    On Error GoTo ErrorHandler
    Dim temp As Variant
    temp = col(key)
    ItemExists = True
    Exit Function
ErrorHandler:
    ItemExists = False
End Function
Sub ConsolidateBOMNewTable()
    On Error GoTo ErrorHandler
    Dim acDoc As AcadDocument
    Dim oldTable As AcadTable
    Dim newTable As AcadTable
    Dim rows As Long, cols As Long
    Dim itemCol As Long, qtyCol As Long, locCol As Long
    Dim locations As New Collection
    Dim items As New Collection
    Dim row As Long, col As Long
    Dim item As Variant, loc As Variant
    Dim qty As Long, total As Long
    Dim hasBlank As Boolean
    Dim progressForm As New progressForm
    Dim totalLocations As Long
    totalLocations = 0
    
    ' Show progress form
    progressForm.show vbModeless
    UpdateProgress progressForm, "Selecting table...", 0
    
    ' Get the active document and modelspace
    Set acDoc = ThisDrawing
    Dim modelSpace As AcadModelSpace
    Set modelSpace = acDoc.modelSpace
    
    ' Show clear instructions in a message box
    MsgBox "IMPORTANT: You will now be asked to select the BOM table." & vbCrLf & vbCrLf & _
           "• Click on the TABLE BORDER (the outline of the table)" & vbCrLf & _
           "• Do NOT click on text inside the table", _
           vbInformation, "Select BOM Table"
    
    ' Prompt user to select the table
    Dim pickPoint(0 To 2) As Double
    Dim entityName As AcadEntity
    
    On Error Resume Next
    ThisDrawing.Utility.GetEntity entityName, pickPoint, "Select the BOM table (click on table border): "
    
    If Err.Number <> 0 Then
        MsgBox "Selection canceled or failed.", vbExclamation, "Selection Error"
        Unload progressForm
        Exit Sub
    End If
    On Error GoTo ErrorHandler
    
    If entityName Is Nothing Then
        MsgBox "No entity selected. Exiting macro.", vbExclamation, "Selection Error"
        Unload progressForm
        Exit Sub
    End If
    
    ' Check if the selected entity is a table
    If TypeOf entityName Is AcadTable Then
        Set oldTable = entityName
    Else
        MsgBox "The selected object is not a table." & vbCrLf & vbCrLf & _
               "Please run the macro again and click on the TABLE BORDER (outline), not on text or other objects.", _
               vbExclamation, "Invalid Selection"
        Unload progressForm
        Exit Sub
    End If
    
    ' Get table dimensions
    rows = oldTable.rows
    cols = oldTable.Columns
    
    UpdateProgress progressForm, "Analyzing table structure...", 10
    
    ' Find ITEM, QTY, and TEMP_LOC columns
    itemCol = -1
    qtyCol = -1
    locCol = -1
    For col = 0 To cols - 1
        Select Case UCase(Trim(oldTable.GetText(1, col)))
            Case "ITEM"
                itemCol = col
            Case "QTY"
                qtyCol = col
            Case "TEMP_LOC"
                locCol = col
        End Select
    Next col
    
    ' Check if all required columns were found
    If itemCol = -1 Or qtyCol = -1 Or locCol = -1 Then
        MsgBox "Could not find ITEM, QTY, or TEMP_LOC columns. Exiting macro."
        Unload progressForm
        Exit Sub
    End If
    
    UpdateProgress progressForm, "Checking location data...", 15
    
    ' Check if TEMP_LOC column has any data
    Dim hasLocations As Boolean
    hasLocations = False
    For row = 2 To rows - 1
        If Trim(oldTable.GetText(row, locCol)) <> "" Then
            hasLocations = True
            Exit For
        End If
    Next row
    
    If Not hasLocations Then
        Dim response As VbMsgBoxResult
        response = MsgBox("The TEMP_LOC column is empty. Would you like to:" & vbCrLf & _
                         "- Click YES to treat all items as 'BLANK' location" & vbCrLf & _
                         "- Click NO to cancel the operation", _
                         vbYesNo + vbQuestion, "Empty Locations")
        
        If response = vbNo Then
            Unload progressForm
            Exit Sub
        End If
        
        ' If user chooses to continue, force "BLANK" location
        hasBlank = True
    End If
    
    UpdateProgress progressForm, "Extracting unique items and locations...", 20
    
    ' Extract unique locations and items with error handling
    For row = 2 To rows - 1
        item = Trim(oldTable.GetText(row, itemCol))
        loc = Trim(oldTable.GetText(row, locCol))
        
        If item <> "" Then
            If Not ItemExists(items, CStr(item)) Then
                items.Add item, CStr(item)
            End If
        End If
        
        If loc <> "" Then
            If Not ItemExists(locations, CStr(loc)) Then
                locations.Add loc, CStr(loc)
                totalLocations = totalLocations + 1
            End If
        Else
            hasBlank = True
        End If
    Next row
    
    ' Add BLANK to locations if there are blank entries
    If hasBlank Then
        If Not ItemExists(locations, "BLANK") Then
            locations.Add "BLANK", "BLANK"
            totalLocations = totalLocations + 1
        End If
    End If
    
    ' Additional check for locations
    If locations.Count = 0 Then
        ' If no locations found and user chose to continue, add BLANK
        locations.Add "BLANK", "BLANK"
        totalLocations = 1
    End If
    
    UpdateProgress progressForm, "Creating new table...", 30
    
    ' Create new table with correct number of columns
    Dim newCols As Long
    newCols = cols - 2 + locations.Count + 1 ' Subtract QTY and TEMP_LOC, add locations and TOTAL
    Dim insertionPoint(0 To 2) As Double
    insertionPoint(0) = oldTable.insertionPoint(0) + oldTable.Width + 50
    insertionPoint(1) = oldTable.insertionPoint(1)
    insertionPoint(2) = oldTable.insertionPoint(2)
    
    Dim rowHeight As Double
    rowHeight = oldTable.GetRowHeight(1)
    
    Set newTable = modelSpace.AddTable(insertionPoint, items.Count + 2, newCols, rowHeight, oldTable.GetColumnWidth(0))
    
    ' Copy table properties
    newTable.Layer = oldTable.Layer
    newTable.StyleName = oldTable.StyleName
    
    ' Set header row height to 60 units
    newTable.SetRowHeight 1, 60
    
    ' Set column widths
    Dim newCol As Long
    newCol = 0
    For col = 0 To cols - 1
        If col <> qtyCol And col <> locCol Then
            newTable.SetColumnWidth newCol, oldTable.GetColumnWidth(col)
            newCol = newCol + 1
        End If
    Next col
    
    ' Set width for location columns and TOTAL
    Dim newColWidth As Double
    newColWidth = oldTable.GetColumnWidth(qtyCol)
    For col = newCol To newCols - 1
        newTable.SetColumnWidth col, newColWidth
    Next col
    
    ' Set row heights for data rows
    For row = 2 To items.Count + 1
        newTable.SetRowHeight row, rowHeight
    Next row
    
    UpdateProgress progressForm, "Populating new table...", 40
    
    ' Set headers with explicit location values
    Dim headerCol As Long
    headerCol = 0
    
    ' Copy original headers except QTY and TEMP_LOC
    For col = 0 To cols - 1
        If col <> qtyCol And col <> locCol Then
            newTable.SetText 1, headerCol, oldTable.GetText(1, col)
            headerCol = headerCol + 1
        End If
    Next col
    
    ' Add location headers with rotation
    For Each loc In locations
        newTable.SetText 1, headerCol, CStr(loc)
        newTable.SetTextRotation 1, headerCol, acDegrees090
        headerCol = headerCol + 1
    Next loc
    
    ' Add TOTAL header with rotation
    newTable.SetText 1, headerCol, "TOTAL"
    newTable.SetTextRotation 1, headerCol, acDegrees090
    
    ' Copy title and merge cells
    newTable.SetText 0, 0, oldTable.GetText(0, 0)
    newTable.MergeCells 0, 0, 0, newCols - 1
    
    ' Set column alignments
    Dim alignmentCol As Long
    alignmentCol = 0
    For col = 0 To cols - 1
        If col <> qtyCol And col <> locCol Then
            Select Case UCase(Trim(oldTable.GetText(1, col)))
                Case "DESCRIPTION", "MANUFACTURER", "SUPPLIER", "PART NO.", "NOTES"
                    ' Set middle-left alignment for all rows in this column
                    For row = 2 To items.Count + 1
                        newTable.SetCellAlignment row, alignmentCol, acMiddleLeft
                    Next row
            End Select
            alignmentCol = alignmentCol + 1
        End If
    Next col
    
    ' Populate data
    Dim newRow As Long
    newRow = 2
    Dim ItemCount As Long
    ItemCount = items.Count
    Dim currentItem As Long
    currentItem = 0
    
    For Each item In items
        ' Copy item data
        headerCol = 0
        For col = 0 To cols - 1
            If col <> qtyCol And col <> locCol Then
                For row = 2 To rows - 1
                    If Trim(oldTable.GetText(row, itemCol)) = item Then
                        newTable.SetText newRow, headerCol, oldTable.GetText(row, col)
                        Exit For
                    End If
                Next row
                headerCol = headerCol + 1
            End If
        Next col
        
        ' Add quantities for each location
        total = 0
        For Each loc In locations
            qty = 0
            For row = 2 To rows - 1
                If Trim(oldTable.GetText(row, itemCol)) = item Then
                    Dim currentLoc As String
                    currentLoc = Trim(oldTable.GetText(row, locCol))
                    
                    If (loc = "BLANK" And currentLoc = "") Or _
                       (currentLoc = loc) Then
                        qty = qty + CLng(oldTable.GetText(row, qtyCol))
                    End If
                End If
            Next row
            
            ' Only write non-zero quantities
            If qty > 0 Then
                newTable.SetText newRow, headerCol, CStr(qty)
            End If
            total = total + qty
            headerCol = headerCol + 1
        Next loc
        
        ' Add total
        newTable.SetText newRow, headerCol, CStr(total)
        
        newRow = newRow + 1
        currentItem = currentItem + 1
        
        ' Update progress with current item count
        UpdateProgress progressForm, "Populating new table... " & currentItem & " of " & ItemCount, _
                       40 + (currentItem / ItemCount) * 60
    Next item
    
    UpdateProgress progressForm, "Complete!", 100
    
    MsgBox "New consolidated BOM table created successfully."
    Unload progressForm
    Exit Sub

ErrorHandler:
    If Err.Number = 91 Then  ' Object not found error
        MsgBox "Error: Unable to process the table. Please check that all columns contain valid data."
    Else
        MsgBox "An error occurred: " & Err.Description
    End If
    Unload progressForm
End Sub
Sub TransferDINRailToBOM()
    ' Variable declarations
    Dim acDoc As AcadDocument
    Dim dinTable As AcadTable
    Dim bomTable As AcadTable
    Dim pickPoint(0 To 2) As Double
    Dim entityName As AcadEntity
    Dim progressForm As Object
    Dim rowCount As Long
    Dim currentRow As Long
    Dim progressValue As Integer
    
    ' Constants
    Const SCALE_FACTOR As Double = 0.001  ' Convert mm to m
    Const DECIMAL_PLACES As Integer = 2   ' Round to 2 decimal places
    
    ' Column indices variables
    Dim dinMfgCol As Long
    Dim dinCatCol As Long
    Dim bomMfgCol As Long
    Dim bomPartCol As Long
    
    ' Initialize objects to Nothing to help with error handling
    Set progressForm = Nothing
    
    ' Main code starts here
    On Error GoTo ErrorHandler
    
    ' Create progress form
    Set progressForm = New progressForm
    progressForm.show vbModeless
    Call UpdateProgress(progressForm, "Initializing...", 0)
    
    ' Get the active document
    Set acDoc = ThisDrawing
    
    Call UpdateProgress(progressForm, "Please select DIN RAIL SUMMARY table...", 5)
    
    ' Show clear instructions in a message box
    MsgBox "IMPORTANT: You will now be asked to select the DIN RAIL SUMMARY table." & vbCrLf & vbCrLf & _
           "• Click on the TABLE BORDER (the outline of the table)" & vbCrLf & _
           "• Do NOT click on text inside the table", _
           vbInformation, "Select DIN RAIL SUMMARY Table"
           
    ' Get DIN RAIL SUMMARY table
    On Error Resume Next
    ThisDrawing.Utility.GetEntity entityName, pickPoint, "Select the DIN RAIL SUMMARY table: "
    If Err.Number <> 0 Then
        MsgBox "Error selecting DIN RAIL SUMMARY table: " & Err.Description
        Unload progressForm
        Exit Sub
    End If
    On Error GoTo ErrorHandler
    
    If entityName Is Nothing Then
        MsgBox "No DIN RAIL SUMMARY table selected. Exiting macro."
        Unload progressForm
        Exit Sub
    End If
    
    If TypeOf entityName Is AcadTable Then
        Set dinTable = entityName
    Else
        MsgBox "Selected entity is not a table. Exiting macro."
        Unload progressForm
        Exit Sub
    End If
    
    Call UpdateProgress(progressForm, "Please select BOM table...", 15)
    
    ' Show clear instructions for BOM table selection
    MsgBox "IMPORTANT: You will now be asked to select the BOM table." & vbCrLf & vbCrLf & _
           "• Click on the TABLE BORDER (the outline of the table)" & vbCrLf & _
           "• Do NOT click on text inside the table", _
           vbInformation, "Select BOM Table"
    
    ' Get BOM table
    On Error Resume Next
    ThisDrawing.Utility.GetEntity entityName, pickPoint, "Select the BOM table: "
    If Err.Number <> 0 Then
        MsgBox "Error selecting BOM table: " & Err.Description
        Unload progressForm
        Exit Sub
    End If
    On Error GoTo ErrorHandler
    
    If entityName Is Nothing Then
        MsgBox "No BOM table selected. Exiting macro."
        Unload progressForm
        Exit Sub
    End If
    
    If TypeOf entityName Is AcadTable Then
        Set bomTable = entityName
    Else
        MsgBox "Selected entity is not a table. Exiting macro."
        Unload progressForm
        Exit Sub
    End If
    
    Call UpdateProgress(progressForm, "Analyzing table structure...", 20)
    
    ' Find required columns in DIN RAIL SUMMARY table
    dinMfgCol = -1
    dinCatCol = -1
    For col = 0 To dinTable.Columns - 1
        Select Case UCase(Trim(dinTable.GetText(1, col)))
            Case "MFG"
                dinMfgCol = col
            Case "CAT"
                dinCatCol = col
        End Select
    Next col
    
    Call UpdateProgress(progressForm, "Locating columns in BOM table...", 25)
    
    ' Find required columns in BOM table
    bomMfgCol = -1
    bomPartCol = -1
    For col = 0 To bomTable.Columns - 1
        Select Case UCase(Trim(bomTable.GetText(1, col)))
            Case "MANUFACTURER"
                bomMfgCol = col
            Case "PART NO."
                bomPartCol = col
        End Select
    Next col
    
    ' Verify all required columns were found
    If dinMfgCol = -1 Or dinCatCol = -1 Then
        MsgBox "Could not find MFG or CAT columns in DIN RAIL SUMMARY table."
        Unload progressForm
        Exit Sub
    End If
    
    If bomMfgCol = -1 Or bomPartCol = -1 Then
        MsgBox "Could not find MANUFACTURER or PART NO. columns in BOM table."
        Unload progressForm
        Exit Sub
    End If
    
    Call UpdateProgress(progressForm, "Preparing for data transfer...", 30)
    
    ' Start undo mark
    acDoc.StartUndoMark
    
    ' Get row count for progress calculation
    rowCount = bomTable.rows - 2 ' Exclude header row
    currentRow = 0
    
    ' Process each row in BOM table
    Dim bomRow As Long
    Dim dinRow As Long
    Dim locationCol As Long
    Dim sourceValue As Double
    Dim scaledValue As Double
    
    Call UpdateProgress(progressForm, "Transferring DIN rail data...", 35)
    
    ' Start from row 2 (after header)
    For bomRow = 2 To bomTable.rows - 1
        currentRow = currentRow + 1
        
        Dim bomMfg As String
        Dim bomPart As String
        bomMfg = Trim(bomTable.GetText(bomRow, bomMfgCol))
        bomPart = Trim(bomTable.GetText(bomRow, bomPartCol))
        
        ' Look for matching row in DIN RAIL SUMMARY
        For dinRow = 2 To dinTable.rows - 1
            Dim dinMfg As String
            Dim dinPart As String
            dinMfg = Trim(dinTable.GetText(dinRow, dinMfgCol))
            dinPart = Trim(dinTable.GetText(dinRow, dinCatCol))
            
            ' If match found, process location columns
            If dinMfg = bomMfg And dinPart = bomPart Then
                ' Process each column after the header columns
                For locationCol = 0 To dinTable.Columns - 1
                    ' Skip non-location columns (MFG, CAT, etc.)
                    If locationCol <> dinMfgCol And locationCol <> dinCatCol Then
                        ' Get location code from header
                        Dim locationCode As String
                        locationCode = Trim(dinTable.GetText(1, locationCol))
                        
                        ' Find matching column in BOM table
                        Dim bomLocationCol As Long
                        For bomLocationCol = 0 To bomTable.Columns - 1
                            If Trim(bomTable.GetText(1, bomLocationCol)) = locationCode Then
                                ' Get and scale the value
                                On Error Resume Next
                                sourceValue = CDbl(dinTable.GetText(dinRow, locationCol))
                                If Err.Number = 0 Then
                                    ' Scale and round the value
                                    scaledValue = Round(sourceValue * SCALE_FACTOR, DECIMAL_PLACES)
                                    ' Format the value to always show 2 decimal places
                                    bomTable.SetText bomRow, bomLocationCol, Format(scaledValue, "0.00")
                                End If
                                On Error GoTo ErrorHandler
                                Exit For
                            End If
                        Next bomLocationCol
                    End If
                Next locationCol
                Exit For  ' Exit DIN row loop once match is found
            End If
        Next dinRow
        
        ' Update progress - scale from 35% to 95%
        progressValue = CInt(35 + (currentRow / rowCount) * 60)
        Call UpdateProgress(progressForm, "Transferring DIN rail data... (" & currentRow & " of " & rowCount & ")", progressValue)
    Next bomRow
    
    ' End undo mark
    acDoc.EndUndoMark
    
    ' Update the display
    acDoc.Regen True
    
    Call UpdateProgress(progressForm, "Transfer completed successfully!", 100)
    
    MsgBox "Transfer completed successfully!"
    Unload progressForm
    Exit Sub

ErrorHandler:
    ' Capture error info first
    Dim errDescription As String
    Dim errNumber As Long
    errDescription = Err.Description
    errNumber = Err.Number
    
    ' Safe cleanup - use On Error Resume Next for cleanup operations
    On Error Resume Next
    
    ' End undo mark if needed
    If Not acDoc Is Nothing Then
        acDoc.EndUndoMark  ' This may fail, but we'll continue
    End If
    
    ' Unload progress form if it exists
    If Not progressForm Is Nothing Then
        Unload progressForm  ' This may fail, but we'll continue
    End If
    
    ' Now report the original error
    If errNumber = 91 Then  ' Object not found error
        MsgBox "Error: Unable to process the tables. Please check that all columns contain valid data.", _
               vbCritical, "Error"
    Else
        MsgBox "An error occurred: " & errDescription & " (Error " & errNumber & ")", _
               vbCritical, "Error"
    End If
End Sub
Sub UpdateSuppliers()
    ' Variable declarations
    Dim acadApp As AcadApplication
    Dim acadDoc As AcadDocument
    Dim objTable As AcadTable
    Dim fso As Object
    Dim csvFile As Object
    Dim dataLine As String
    Dim csvData() As String
    Dim manufacturerCol As Integer
    Dim supplierCol As Integer
    Dim partNoCol As Integer
    Dim i As Long, j As Long
    Dim pickPoint(0 To 2) As Double
    Dim progressForm As Object
    Dim rowCount As Long
    Dim currentRow As Long
    Dim progressValue As Integer
    
    ' Initialize objects to Nothing to help with error handling
    Set fso = Nothing
    Set csvFile = Nothing
    Set progressForm = Nothing
    
    ' Main code starts here
    On Error GoTo ErrorHandler
    
    ' Create progress form if possible
    Set progressForm = New progressForm
    progressForm.show vbModeless
    Call UpdateProgress(progressForm, "Initializing...", 0)
    
    ' Get the AutoCAD application and document
    Set acadApp = GetObject(, "AutoCAD.Application")
    Set acadDoc = acadApp.ActiveDocument
    
    ' Show clear instructions in a message box
    MsgBox "IMPORTANT: You will now be asked to select a BOM table." & vbCrLf & vbCrLf & _
           "• Click on the TABLE BORDER (the outline of the table)" & vbCrLf & _
           "• Do NOT click on text inside the table", _
           vbInformation, "Select BOM Table"
    
    Call UpdateProgress(progressForm, "Waiting for table selection...", 5)
    
    ' Prompt user to select the table
    On Error Resume Next
    Dim objSel As Object
    acadDoc.Utility.GetEntity objSel, pickPoint, "Select table: "
    
    If Err.Number <> 0 Then
        MsgBox "No table selected or invalid selection.", vbExclamation, "Selection Error"
        Unload progressForm
        Exit Sub
    End If
    
    If TypeOf objSel Is AcadTable Then
        Set objTable = objSel
    Else
        MsgBox "Selected object is not a table." & vbCrLf & vbCrLf & _
               "Please run the macro again and click on the TABLE BORDER (outline), not on text or other objects.", _
               vbExclamation, "Invalid Selection"
        Unload progressForm
        Exit Sub
    End If
    On Error GoTo ErrorHandler
    
    Call UpdateProgress(progressForm, "Analyzing table structure...", 10)
    
    ' Find MANUFACTURER, SUPPLIER, and PART NO. columns in the table
    manufacturerCol = -1
    supplierCol = -1
    partNoCol = -1
    
    For i = 0 To objTable.Columns - 1
        Select Case UCase(Trim(objTable.GetText(1, i)))
            Case "MANUFACTURER"
                manufacturerCol = i
            Case "SUPPLIER"
                supplierCol = i
            Case "PART NO."
                partNoCol = i
        End Select
    Next i
    
    If manufacturerCol = -1 Or supplierCol = -1 Then
        MsgBox "Could not find MANUFACTURER or SUPPLIER columns in the table.", vbExclamation, "Missing Columns"
        Unload progressForm
        Exit Sub
    End If
    
    ' Define CSV file paths
    Dim commonCsvPath As String
    Dim specialCsvPath As String
    
    commonCsvPath = "C:\Users\user\Documents\ACADE_VBA\suppliers-common.csv"
    specialCsvPath = "C:\Users\user\Documents\ACADE_VBA\suppliers-special.csv"
    
    ' Check if CSV files exist
    Set fso = CreateObject("Scripting.FileSystemObject")
    
    If Not fso.FileExists(commonCsvPath) Then
        MsgBox "Could not find suppliers-common.csv file at: " & commonCsvPath, vbExclamation, "File Not Found"
        Unload progressForm
        Exit Sub
    End If
    
    ' Start undo mark
    acadDoc.StartUndoMark
    
    ' Get row count for progress calculation
    rowCount = objTable.rows - 1 ' Exclude header row
    currentRow = 0
    
    Call UpdateProgress(progressForm, "Processing common suppliers...", 15)
    
    '-------------------------------------------------------------------------------
    ' STEP 1: Update from suppliers-common.csv (MANUFACTURER,SUPPLIER)
    '-------------------------------------------------------------------------------
    For i = 2 To objTable.rows - 1 ' Start from 2 to skip header rows
        currentRow = currentRow + 1
        Dim tableManufacturer As String
        tableManufacturer = UCase(Trim(objTable.GetText(i, manufacturerCol)))
        
        ' Skip empty manufacturers
        If tableManufacturer <> "" Then
            ' Open the common suppliers file
            Set csvFile = fso.OpenTextFile(commonCsvPath, 1) ' 1 = ForReading
            
            ' Search through CSV for matching manufacturer
            Do Until csvFile.AtEndOfStream
                dataLine = csvFile.ReadLine
                csvData = Split(dataLine, ",")
                
                ' Clean up CSV data
                If UBound(csvData) >= 1 Then
                    Dim csvManufacturer As String
                    csvManufacturer = UCase(Trim(csvData(0)))
                    
                    ' If manufacturer matches, update supplier
                    If csvManufacturer = tableManufacturer Then
                        objTable.SetText i, supplierCol, Trim(csvData(1))
                        Exit Do
                    End If
                End If
            Loop
            
            ' Close the file
            csvFile.Close
            Set csvFile = Nothing ' Clear the object after closing
        End If
        
        ' Update progress - first half is for common suppliers (15% to 60%)
        progressValue = CInt(15 + (currentRow / rowCount) * 45)
        Call UpdateProgress(progressForm, "Processing common suppliers... (" & currentRow & " of " & rowCount & ")", progressValue)
    Next i
    
    '-------------------------------------------------------------------------------
    ' STEP 2: Update from suppliers-special.csv (MANUFACTURER,PART NO.,SUPPLIER)
    '-------------------------------------------------------------------------------
    If fso.FileExists(specialCsvPath) And partNoCol <> -1 Then
        Call UpdateProgress(progressForm, "Processing special suppliers...", 60)
        
        currentRow = 0
        For i = 2 To objTable.rows - 1 ' Start from 2 to skip header rows
            currentRow = currentRow + 1
            tableManufacturer = UCase(Trim(objTable.GetText(i, manufacturerCol)))
            Dim tablePartNo As String
            tablePartNo = UCase(Trim(objTable.GetText(i, partNoCol)))
            
            ' Skip empty manufacturers or part numbers
            If tableManufacturer <> "" And tablePartNo <> "" Then
                ' Open the special suppliers file
                Set csvFile = fso.OpenTextFile(specialCsvPath, 1) ' 1 = ForReading
                
                ' Search through CSV for matching manufacturer and part number
                Do Until csvFile.AtEndOfStream
                    dataLine = csvFile.ReadLine
                    csvData = Split(dataLine, ",")
                    
                    ' Clean up CSV data - needs MANUFACTURER, PART NO., SUPPLIER (3 columns)
                    If UBound(csvData) >= 2 Then
                        Dim csvSpecialManufacturer As String
                        Dim csvSpecialPartNo As String
                        
                        csvSpecialManufacturer = UCase(Trim(csvData(0)))
                        csvSpecialPartNo = UCase(Trim(csvData(1)))
                        
                        ' If both manufacturer and part number match, update supplier
                        If csvSpecialManufacturer = tableManufacturer And csvSpecialPartNo = tablePartNo Then
                            objTable.SetText i, supplierCol, Trim(csvData(2))
                            Exit Do
                        End If
                    End If
                Loop
                
                ' Close the file
                csvFile.Close
                Set csvFile = Nothing ' Clear the object after closing
            End If
            
            ' Update progress - second half is for special suppliers (60% to 95%)
            progressValue = CInt(60 + (currentRow / rowCount) * 35)
            Call UpdateProgress(progressForm, "Processing special suppliers... (" & currentRow & " of " & rowCount & ")", progressValue)
        Next i
    End If
    
    ' Clean up
    Set fso = Nothing
    
    ' End undo mark
    acadDoc.EndUndoMark
    
    Call UpdateProgress(progressForm, "Update complete!", 100)
    
    MsgBox "Table update complete!", vbInformation, "Success"
    Unload progressForm
    Exit Sub
    
ErrorHandler:
    ' Capture error info first
    Dim errDescription As String
    Dim errNumber As Long
    errDescription = Err.Description
    errNumber = Err.Number
    
    ' Safe cleanup - use On Error Resume Next for cleanup operations
    On Error Resume Next
    
    ' Clean up csvFile - don't try to check if it's Nothing
    If Not csvFile Is Nothing Then
        csvFile.Close  ' This may fail, but we'll continue
    End If
    Set csvFile = Nothing
    
    ' Clean up other objects
    Set fso = Nothing
    
    ' End undo mark if needed
    If Not acadDoc Is Nothing Then
        acadDoc.EndUndoMark  ' This may fail, but we'll continue
    End If
    
    ' Unload progress form if it exists
    If Not progressForm Is Nothing Then
        Unload progressForm  ' This may fail, but we'll continue
    End If
    
    ' Now report the original error
    MsgBox "An error occurred: " & errDescription & " (Error " & errNumber & ")", _
           vbCritical, "Error"
End Sub
Sub UpdateNotes()
    ' Variable declarations
    Dim acadApp As AcadApplication
    Dim acadDoc As AcadDocument
    Dim csvFilePath As String
    Dim objTable As AcadTable
    Dim fso As Object
    Dim csvFile As Object
    Dim dataLine As String
    Dim csvData() As String
    Dim manufacturerCol As Integer
    Dim partNoCol As Integer
    Dim notesCol As Integer
    Dim i As Long, j As Long
    Dim pickPoint(0 To 2) As Double
    Dim progressForm As Object
    Dim rowCount As Long
    Dim currentRow As Long
    Dim progressValue As Integer
    
    ' Initialize objects to Nothing to help with error handling
    Set fso = Nothing
    Set csvFile = Nothing
    Set progressForm = Nothing
    
    ' Main code starts here
    On Error GoTo ErrorHandler
    
    ' Create progress form
    Set progressForm = New progressForm
    progressForm.show vbModeless
    Call UpdateProgress(progressForm, "Initializing...", 0)
    
    ' Get the AutoCAD application and document
    Set acadApp = GetObject(, "AutoCAD.Application")
    Set acadDoc = acadApp.ActiveDocument
    
    ' Show clear instructions in a message box
    MsgBox "IMPORTANT: You will now be asked to select a BOM table." & vbCrLf & vbCrLf & _
           "• Click on the TABLE BORDER (the outline of the table)" & vbCrLf & _
           "• Do NOT click on text inside the table", _
           vbInformation, "Select BOM Table"
    
    Call UpdateProgress(progressForm, "Waiting for table selection...", 5)
    
    ' Prompt user to select the table
    On Error Resume Next
    Dim objSel As Object
    acadDoc.Utility.GetEntity objSel, pickPoint, "Select table: "
    
    If Err.Number <> 0 Then
        MsgBox "No table selected or invalid selection.", vbExclamation, "Selection Error"
        Unload progressForm
        Exit Sub
    End If
    
    If TypeOf objSel Is AcadTable Then
        Set objTable = objSel
    Else
        MsgBox "Selected object is not a table." & vbCrLf & vbCrLf & _
               "Please run the macro again and click on the TABLE BORDER (outline), not on text or other objects.", _
               vbExclamation, "Invalid Selection"
        Unload progressForm
        Exit Sub
    End If
    On Error GoTo ErrorHandler
    
    Call UpdateProgress(progressForm, "Analyzing table structure...", 10)
    
    ' Get CSV file path
    csvFilePath = "C:\Users\user\Documents\ACADE_VBA\notes.csv"
    If csvFilePath = "False" Then
        Unload progressForm
        Exit Sub
    End If
    
    ' Find required columns in the table
    manufacturerCol = -1
    partNoCol = -1
    notesCol = -1
    
    For i = 0 To objTable.Columns - 1
        Select Case UCase(Trim(objTable.GetText(1, i)))
            Case "MANUFACTURER"
                manufacturerCol = i
            Case "PART NO."
                partNoCol = i
            Case "NOTES"
                notesCol = i
        End Select
    Next i
    
    If manufacturerCol = -1 Or partNoCol = -1 Or notesCol = -1 Then
        MsgBox "Could not find required columns (MANUFACTURER, PART NO., or NOTES) in the table.", _
               vbExclamation, "Missing Columns"
        Unload progressForm
        Exit Sub
    End If
    
    Call UpdateProgress(progressForm, "Checking CSV file...", 15)
    
    ' Check if CSV file exists
    Set fso = CreateObject("Scripting.FileSystemObject")
    
    If Not fso.FileExists(csvFilePath) Then
        MsgBox "Could not find notes.csv file at: " & csvFilePath, vbExclamation, "File Not Found"
        Unload progressForm
        Exit Sub
    End If
    
    ' Open CSV file
    Set csvFile = fso.OpenTextFile(csvFilePath, 1) ' 1 = ForReading
    
    ' Start undo mark
    acadDoc.StartUndoMark
    
    ' Get row count for progress calculation
    rowCount = objTable.rows - 1 ' Exclude header row
    currentRow = 0
    
    Call UpdateProgress(progressForm, "Processing notes...", 20)
    
    ' Process each row in the table
    For i = 2 To objTable.rows - 1 ' Start from 2 to skip header rows
        currentRow = currentRow + 1
        Dim tableManufacturer As String
        Dim tablePartNo As String
        
        tableManufacturer = UCase(Trim(objTable.GetText(i, manufacturerCol)))
        tablePartNo = UCase(Trim(objTable.GetText(i, partNoCol)))
        
        ' Skip empty entries
        If tableManufacturer <> "" And tablePartNo <> "" Then
            ' Reset file pointer to beginning
            csvFile.Close
            Set csvFile = fso.OpenTextFile(csvFilePath, 1)
            
            ' Search through CSV for matching manufacturer and part number
            Do Until csvFile.AtEndOfStream
                dataLine = csvFile.ReadLine
                csvData = Split(dataLine, ",")
                
                ' Clean up CSV data
                If UBound(csvData) >= 2 Then
                    Dim csvManufacturer As String
                    Dim csvPartNo As String
                    
                    csvManufacturer = UCase(Trim(csvData(0)))
                    csvPartNo = UCase(Trim(csvData(1)))
                    
                    ' If both manufacturer and part number match, update notes
                    If csvManufacturer = tableManufacturer And csvPartNo = tablePartNo Then
                        objTable.SetText i, notesCol, Trim(csvData(2))
                        Exit Do
                    End If
                End If
            Loop
        End If
        
        ' Update progress - scale from 20% to 95%
        progressValue = CInt(20 + (currentRow / rowCount) * 75)
        Call UpdateProgress(progressForm, "Processing notes... (" & currentRow & " of " & rowCount & ")", progressValue)
    Next i
    
    ' Clean up
    csvFile.Close
    Set csvFile = Nothing
    Set fso = Nothing
    
    ' End undo mark
    acadDoc.EndUndoMark
    
    Call UpdateProgress(progressForm, "Update complete!", 100)
    
    MsgBox "Table update complete!", vbInformation, "Success"
    Unload progressForm
    Exit Sub
    
ErrorHandler:
    ' Capture error info first
    Dim errDescription As String
    Dim errNumber As Long
    errDescription = Err.Description
    errNumber = Err.Number
    
    ' Safe cleanup - use On Error Resume Next for cleanup operations
    On Error Resume Next
    
    ' Clean up csvFile
    If Not csvFile Is Nothing Then
        csvFile.Close  ' This may fail, but we'll continue
    End If
    Set csvFile = Nothing
    
    ' Clean up other objects
    Set fso = Nothing
    
    ' End undo mark if needed
    If Not acadDoc Is Nothing Then
        acadDoc.EndUndoMark  ' This may fail, but we'll continue
    End If
    
    ' Unload progress form if it exists
    If Not progressForm Is Nothing Then
        Unload progressForm  ' This may fail, but we'll continue
    End If
    
    ' Now report the original error
    MsgBox "An error occurred: " & errDescription & " (Error " & errNumber & ")", _
           vbCritical, "Error"
End Sub

Sub CreateItemComparisonTable()
    On Error GoTo ErrorHandler
    
    ' Declare variables
    Dim acDoc As AcadDocument
    Dim panelTable As AcadTable, schematicTable As AcadTable, comparisonTable As AcadTable
    Dim i As Long, j As Long, row As Long
    Dim insertionPoint(0 To 2) As Double
    Dim panelPickPoint(0 To 2) As Double, schematicPickPoint(0 To 2) As Double
    Dim panelItems As Object, schematicItems As Object, allItems As Object
    Dim panelQty As Object, schematicQty As Object
    Dim currentItem As Variant, partNo As String, manufacturer As String
    Dim panelQtyValue As Integer, schematicQtyValue As Integer, difference As Integer
    Dim progressFrm As New progressForm
    
    ' Get the current document
    Set acDoc = ThisDrawing
    
    ' Show progress form
    progressFrm.show vbModeless
    UpdateProgress progressFrm, "Starting process...", 0
    
    ' Create dictionary objects for collecting data
    Set panelItems = CreateObject("Scripting.Dictionary")
    Set schematicItems = CreateObject("Scripting.Dictionary")
    Set allItems = CreateObject("Scripting.Dictionary")
    Set panelQty = CreateObject("Scripting.Dictionary")
    Set schematicQty = CreateObject("Scripting.Dictionary")
    
    ' Prompt user to select Panel table
    UpdateProgress progressFrm, "Select PANEL ITEM SUMMARY table...", 5
    MsgBox "Please select the PANEL ITEM SUMMARY table (click on table border)", vbInformation, "Select Panel Table"
    
    On Error Resume Next
    acDoc.Utility.GetEntity panelTable, panelPickPoint, "Select the PANEL ITEM SUMMARY table: "
    If Err.Number <> 0 Or Not TypeOf panelTable Is AcadTable Then
        MsgBox "Invalid selection or operation canceled.", vbExclamation
        Unload progressFrm
        Exit Sub
    End If
    On Error GoTo ErrorHandler
    
    ' Prompt user to select Schematic table
    UpdateProgress progressFrm, "Select SCHEMATIC ITEM SUMMARY table...", 10
    MsgBox "Please select the SCHEMATIC ITEM SUMMARY table (click on table border)", vbInformation, "Select Schematic Table"
    
    On Error Resume Next
    acDoc.Utility.GetEntity schematicTable, schematicPickPoint, "Select the SCHEMATIC ITEM SUMMARY table: "
    If Err.Number <> 0 Or Not TypeOf schematicTable Is AcadTable Then
        MsgBox "Invalid selection or operation canceled.", vbExclamation
        Unload progressFrm
        Exit Sub
    End If
    On Error GoTo ErrorHandler
    
    ' Verify tables have the expected columns
    UpdateProgress progressFrm, "Verifying table structure...", 15
    If panelTable.Columns < 4 Or schematicTable.Columns < 4 Then
        MsgBox "One or both tables don't have the required columns.", vbExclamation
        Unload progressFrm
        Exit Sub
    End If
    
    ' Process Panel table data
    UpdateProgress progressFrm, "Processing PANEL table data...", 20
    For i = 2 To panelTable.rows - 1 ' Start from row 2 (skip title and header)
        Dim itemValue As String
        itemValue = Trim(panelTable.GetText(i, 0)) ' ITEM column
        
        If itemValue <> "" Then
            ' Store item in panelItems dictionary
            If Not panelItems.Exists(itemValue) Then
                panelItems.Add itemValue, i
            End If
            
            ' Store item in allItems dictionary
            If Not allItems.Exists(itemValue) Then
                allItems.Add itemValue, True
            End If
            
            ' Store quantity
            If Not panelQty.Exists(itemValue) Then
                ' First occurrence of this item
                panelQty.Add itemValue, CInt(panelTable.GetText(i, 3)) ' QTY column
            Else
                ' Item already exists, sum the quantities
                panelQty(itemValue) = panelQty(itemValue) + CInt(panelTable.GetText(i, 3))
            End If
        End If
        
        ' Update progress periodically
        If i Mod 5 = 0 Then
            UpdateProgress progressFrm, "Processing PANEL table: " & i & " of " & panelTable.rows, 20 + (10 * i / panelTable.rows)
        End If
    Next i
    
    ' Process Schematic table data
    UpdateProgress progressFrm, "Processing SCHEMATIC table data...", 35
    For i = 2 To schematicTable.rows - 1 ' Start from row 2 (skip title and header)
        itemValue = Trim(schematicTable.GetText(i, 0)) ' ITEM column
        
        If itemValue <> "" Then
            ' Store item in schematicItems dictionary
            If Not schematicItems.Exists(itemValue) Then
                schematicItems.Add itemValue, i
            End If
            
            ' Add to allItems if not already there
            If Not allItems.Exists(itemValue) Then
                allItems.Add itemValue, True
            End If
            
            ' Store quantity
            If Not schematicQty.Exists(itemValue) Then
                ' First occurrence of this item
                schematicQty.Add itemValue, CInt(schematicTable.GetText(i, 3)) ' QTY column
            Else
                ' Item already exists, sum the quantities
                schematicQty(itemValue) = schematicQty(itemValue) + CInt(schematicTable.GetText(i, 3))
            End If
        End If
        
        ' Update progress periodically
        If i Mod 5 = 0 Then
            UpdateProgress progressFrm, "Processing SCHEMATIC table: " & i & " of " & schematicTable.rows, 35 + (10 * i / schematicTable.rows)
        End If
    Next i
    
    ' Create insertion point at (0,0,0) as requested
    UpdateProgress progressFrm, "Creating comparison table...", 50
    insertionPoint(0) = 0
    insertionPoint(1) = 0
    insertionPoint(2) = 0
    
    ' Create new comparison table
    Dim totalRows As Long
    totalRows = allItems.Count + 2 ' +2 for title and header rows
    
    ' Create table with 7 columns
    Set comparisonTable = acDoc.modelSpace.AddTable(insertionPoint, totalRows, 7, 25, 100)
    
    ' Copy style from panel table
    On Error Resume Next
    comparisonTable.StyleName = panelTable.StyleName
    comparisonTable.Layer = panelTable.Layer
    
    ' Copy text heights for different row types
    comparisonTable.SetTextHeight acTitleRow, panelTable.GetTextHeight(acTitleRow)
    comparisonTable.SetTextHeight acHeaderRow, panelTable.GetTextHeight(acHeaderRow)
    comparisonTable.SetTextHeight acDataRow, panelTable.GetTextHeight(acDataRow)
    
    ' Set column widths
    UpdateProgress progressFrm, "Setting table properties...", 55
    comparisonTable.SetColumnWidth 0, 50  ' ITEM
    comparisonTable.SetColumnWidth 1, 150 ' MANUFACTURER
    comparisonTable.SetColumnWidth 2, 150 ' PART NO
    comparisonTable.SetColumnWidth 3, 60  ' PANEL-QTY
    comparisonTable.SetColumnWidth 4, 60  ' SCHEM.-QTY
    comparisonTable.SetColumnWidth 5, 60  ' DIFFERENCE
    comparisonTable.SetColumnWidth 6, 100 ' NOTES
    
    ' Set title row
    comparisonTable.SetText 0, 0, "ITEM QTY COMPARISON"
    comparisonTable.MergeCells 0, 0, 0, 6 ' Merge title across all columns
    comparisonTable.SetAlignment 0, acMiddleCenter
    
    ' Set header row
    comparisonTable.SetText 1, 0, "ITEM"
    comparisonTable.SetText 1, 1, "MANUFACTURER"
    comparisonTable.SetText 1, 2, "PART NO."
    comparisonTable.SetText 1, 3, "PANEL-QTY"
    comparisonTable.SetText 1, 4, "SCHEM.-QTY"
    comparisonTable.SetText 1, 5, "DIFFERENCE"
    comparisonTable.SetText 1, 6, "NOTES"
    
    ' Rotate text in the header row for specified columns
    comparisonTable.SetTextRotation 1, 3, acDegrees090
    comparisonTable.SetTextRotation 1, 4, acDegrees090
    comparisonTable.SetTextRotation 1, 5, acDegrees090
    
    ' Adjust header row height to accommodate rotated text
    comparisonTable.SetRowHeight 1, 60
    
    ' Populate table with data
    UpdateProgress progressFrm, "Preparing data for table...", 60
    row = 2 ' Start at row 2 (after title and header)
    
    ' Convert allItems keys to an array for sorting
    Dim sortedItems() As String
    ReDim sortedItems(allItems.Count - 1)
    
    i = 0
    For Each currentItem In allItems.Keys
        sortedItems(i) = currentItem
        i = i + 1
    Next
    
    ' Simple bubble sort (for simplicity - can be improved)
    UpdateProgress progressFrm, "Sorting items...", 65
    Dim temp As String
    For i = LBound(sortedItems) To UBound(sortedItems) - 1
        For j = i + 1 To UBound(sortedItems)
            ' Try numeric comparison if both are numbers
            If IsNumeric(sortedItems(i)) And IsNumeric(sortedItems(j)) Then
                If CInt(sortedItems(i)) > CInt(sortedItems(j)) Then
                    temp = sortedItems(i)
                    sortedItems(i) = sortedItems(j)
                    sortedItems(j) = temp
                End If
            ElseIf sortedItems(i) > sortedItems(j) Then
                ' String comparison
                temp = sortedItems(i)
                sortedItems(i) = sortedItems(j)
                sortedItems(j) = temp
            End If
        Next j
    Next i
    
    ' Fill data in order
    UpdateProgress progressFrm, "Populating comparison table...", 70
    For i = LBound(sortedItems) To UBound(sortedItems)
        currentItem = sortedItems(i)
        
        ' Set ITEM
        comparisonTable.SetText row, 0, currentItem
        
        ' Get MANUFACTURER and PART NO.
        manufacturer = ""
        partNo = ""
        
        If panelItems.Exists(currentItem) Then
            Dim panelRow As Long
            panelRow = panelItems(currentItem)
            manufacturer = panelTable.GetText(panelRow, 1)
            partNo = panelTable.GetText(panelRow, 2)
        ElseIf schematicItems.Exists(currentItem) Then
            Dim schematicRow As Long
            schematicRow = schematicItems(currentItem)
            manufacturer = schematicTable.GetText(schematicRow, 1)
            partNo = schematicTable.GetText(schematicRow, 2)
        End If
        
        ' Set MANUFACTURER and PART NO.
        comparisonTable.SetText row, 1, manufacturer
        comparisonTable.SetText row, 2, partNo
        
        ' Set quantities
        panelQtyValue = 0
        schematicQtyValue = 0
        
        If panelQty.Exists(currentItem) Then
            panelQtyValue = panelQty(currentItem)
            comparisonTable.SetText row, 3, CStr(panelQtyValue)
        End If
        
        If schematicQty.Exists(currentItem) Then
            schematicQtyValue = schematicQty(currentItem)
            comparisonTable.SetText row, 4, CStr(schematicQtyValue)
        End If
        
        ' Calculate difference
        difference = panelQtyValue - schematicQtyValue
        If difference <> 0 Then
            comparisonTable.SetText row, 5, CStr(difference)
        End If
        
        ' Check if all three quantity cells have content and color them
        If panelQtyValue <> 0 And schematicQtyValue <> 0 And difference <> 0 Then
            ' Set background color to 242 for all three cells
            Dim cellgbcol As New AcadAcCmColor
            On Error Resume Next
            Set cellbgcol = comparisonTable.GetCellBackgroundColor(row, 3)
            cellbgcol.SetRGB 204, 0, 51
            comparisonTable.SetCellBackgroundColor row, 3, cellbgcol
            comparisonTable.SetCellBackgroundColor row, 4, cellbgcol
            comparisonTable.SetCellBackgroundColor row, 5, cellbgcol
            On Error GoTo ErrorHandler
        End If
        
        ' NOTES column left blank
        
        row = row + 1
        
        ' Update progress periodically
        If i Mod 5 = 0 Then
            UpdateProgress progressFrm, "Populating table: " & i & " of " & UBound(sortedItems), 70 + (25 * i / UBound(sortedItems))
        End If
    Next i
    
    ' Update table and zoom to see it
    UpdateProgress progressFrm, "Finalizing table...", 95
    comparisonTable.Update
    acDoc.Application.ZoomExtents
    
    UpdateProgress progressFrm, "Process completed", 100
    
    MsgBox "Comparison table created successfully at coordinates (0,0).", vbInformation
    Unload progressFrm
    Exit Sub
    
ErrorHandler:
    MsgBox "An error occurred: " & Err.Number & " - " & Err.Description, vbExclamation, "Error"
    Unload progressFrm
End Sub

Sub CreateItemComparisonTable2()
    On Error GoTo ErrorHandler
    
    ' Declare variables
    Dim acDoc As AcadDocument
    Dim panelTable As AcadTable, schematicTable As AcadTable, sldTable As AcadTable, comparisonTable As AcadTable
    Dim i As Long, j As Long, row As Long
    Dim insertionPoint(0 To 2) As Double
    Dim panelPickPoint(0 To 2) As Double, schematicPickPoint(0 To 2) As Double, sldPickPoint(0 To 2) As Double
    Dim panelItems As Object, schematicItems As Object, sldItems As Object, allItems As Object
    Dim panelQty As Object, schematicQty As Object, sldQty As Object
    Dim currentItem As Variant, partNo As String, manufacturer As String
    Dim panelQtyValue As Integer, schematicQtyValue As Integer, sldQtyValue As Integer, difference As Integer
    Dim progressFrm As New progressForm
    
    ' Get the current document
    Set acDoc = ThisDrawing
    
    ' Show progress form
    progressFrm.show vbModeless
    UpdateProgress progressFrm, "Starting process...", 0
    
    ' Create dictionary objects for collecting data
    Set panelItems = CreateObject("Scripting.Dictionary")
    Set schematicItems = CreateObject("Scripting.Dictionary")
    Set sldItems = CreateObject("Scripting.Dictionary")
    Set allItems = CreateObject("Scripting.Dictionary")
    Set panelQty = CreateObject("Scripting.Dictionary")
    Set schematicQty = CreateObject("Scripting.Dictionary")
    Set sldQty = CreateObject("Scripting.Dictionary")
    
    ' Prompt user to select Panel table
    UpdateProgress progressFrm, "Select PANEL ITEM SUMMARY table...", 3
    MsgBox "Please select the PANEL ITEM SUMMARY table (click on table border)", vbInformation, "Select Panel Table"
    
    On Error Resume Next
    acDoc.Utility.GetEntity panelTable, panelPickPoint, "Select the PANEL ITEM SUMMARY table: "
    If Err.Number <> 0 Or Not TypeOf panelTable Is AcadTable Then
        MsgBox "Invalid selection or operation canceled.", vbExclamation
        Unload progressFrm
        Exit Sub
    End If
    On Error GoTo ErrorHandler
    
    ' Prompt user to select Schematic table
    UpdateProgress progressFrm, "Select SCHEMATIC ITEM SUMMARY table...", 7
    MsgBox "Please select the SCHEMATIC ITEM SUMMARY table (click on table border)", vbInformation, "Select Schematic Table"
    
    On Error Resume Next
    acDoc.Utility.GetEntity schematicTable, schematicPickPoint, "Select the SCHEMATIC ITEM SUMMARY table: "
    If Err.Number <> 0 Or Not TypeOf schematicTable Is AcadTable Then
        MsgBox "Invalid selection or operation canceled.", vbExclamation
        Unload progressFrm
        Exit Sub
    End If
    On Error GoTo ErrorHandler
    
    ' Prompt user to select SLD table
    UpdateProgress progressFrm, "Select SLD ITEM SUMMARY table...", 10
    MsgBox "Please select the SLD ITEM SUMMARY table (click on table border)", vbInformation, "Select SLD Table"
    
    On Error Resume Next
    acDoc.Utility.GetEntity sldTable, sldPickPoint, "Select the SLD ITEM SUMMARY table: "
    If Err.Number <> 0 Or Not TypeOf sldTable Is AcadTable Then
        MsgBox "Invalid selection or operation canceled.", vbExclamation
        Unload progressFrm
        Exit Sub
    End If
    On Error GoTo ErrorHandler
    
    ' Verify tables have the expected columns
    UpdateProgress progressFrm, "Verifying table structure...", 15
    If panelTable.Columns < 4 Or schematicTable.Columns < 4 Or sldTable.Columns < 4 Then
        MsgBox "One or more tables don't have the required columns.", vbExclamation
        Unload progressFrm
        Exit Sub
    End If
    
    ' Process Panel table data
    UpdateProgress progressFrm, "Processing PANEL table data...", 20
    For i = 2 To panelTable.rows - 1 ' Start from row 2 (skip title and header)
        Dim itemValue As String
        itemValue = Trim(panelTable.GetText(i, 0)) ' ITEM column
        
        If itemValue <> "" Then
            ' Store item in panelItems dictionary
            If Not panelItems.Exists(itemValue) Then
                panelItems.Add itemValue, i
            End If
            
            ' Store item in allItems dictionary
            If Not allItems.Exists(itemValue) Then
                allItems.Add itemValue, True
            End If
            
            ' Store quantity
            If Not panelQty.Exists(itemValue) Then
                ' First occurrence of this item
                panelQty.Add itemValue, CInt(panelTable.GetText(i, 3)) ' QTY column
            Else
                ' Item already exists, sum the quantities
                panelQty(itemValue) = panelQty(itemValue) + CInt(panelTable.GetText(i, 3))
            End If
        End If
        
        ' Update progress periodically
        If i Mod 5 = 0 Then
            UpdateProgress progressFrm, "Processing PANEL table: " & i & " of " & panelTable.rows, 20 + (5 * i / panelTable.rows)
        End If
    Next i
    
    ' Process Schematic table data
    UpdateProgress progressFrm, "Processing SCHEMATIC table data...", 30
    For i = 2 To schematicTable.rows - 1 ' Start from row 2 (skip title and header)
        itemValue = Trim(schematicTable.GetText(i, 0)) ' ITEM column
        
        If itemValue <> "" Then
            ' Store item in schematicItems dictionary
            If Not schematicItems.Exists(itemValue) Then
                schematicItems.Add itemValue, i
            End If
            
            ' Add to allItems if not already there
            If Not allItems.Exists(itemValue) Then
                allItems.Add itemValue, True
            End If
            
            ' Store quantity
            If Not schematicQty.Exists(itemValue) Then
                ' First occurrence of this item
                schematicQty.Add itemValue, CInt(schematicTable.GetText(i, 3)) ' QTY column
            Else
                ' Item already exists, sum the quantities
                schematicQty(itemValue) = schematicQty(itemValue) + CInt(schematicTable.GetText(i, 3))
            End If
        End If
        
        ' Update progress periodically
        If i Mod 5 = 0 Then
            UpdateProgress progressFrm, "Processing SCHEMATIC table: " & i & " of " & schematicTable.rows, 30 + (5 * i / schematicTable.rows)
        End If
    Next i
    
    ' Process SLD table data
    UpdateProgress progressFrm, "Processing SLD table data...", 40
    For i = 2 To sldTable.rows - 1 ' Start from row 2 (skip title and header)
        itemValue = Trim(sldTable.GetText(i, 0)) ' ITEM column
        
        If itemValue <> "" Then
            ' Store item in sldItems dictionary
            If Not sldItems.Exists(itemValue) Then
                sldItems.Add itemValue, i
            End If
            
            ' Add to allItems if not already there
            If Not allItems.Exists(itemValue) Then
                allItems.Add itemValue, True
            End If
            
            ' Store quantity
            If Not sldQty.Exists(itemValue) Then
                ' First occurrence of this item
                sldQty.Add itemValue, CInt(sldTable.GetText(i, 3)) ' QTY column
            Else
                ' Item already exists, sum the quantities
                sldQty(itemValue) = sldQty(itemValue) + CInt(sldTable.GetText(i, 3))
            End If
        End If
        
        ' Update progress periodically
        If i Mod 5 = 0 Then
            UpdateProgress progressFrm, "Processing SLD table: " & i & " of " & sldTable.rows, 40 + (5 * i / sldTable.rows)
        End If
    Next i
    
    ' Create insertion point at (0,0,0) as requested
    UpdateProgress progressFrm, "Creating comparison table...", 50
    insertionPoint(0) = 0
    insertionPoint(1) = 0
    insertionPoint(2) = 0
    
    ' Create new comparison table
    Dim totalRows As Long
    totalRows = allItems.Count + 2 ' +2 for title and header rows
    
    ' Create table with 9 columns (added SLD-QTY)
    Set comparisonTable = acDoc.modelSpace.AddTable(insertionPoint, totalRows, 9, 25, 100)
    
    ' Copy style from panel table
    On Error Resume Next
    comparisonTable.StyleName = panelTable.StyleName
    comparisonTable.Layer = panelTable.Layer
    
    ' Copy text heights for different row types
    comparisonTable.SetTextHeight acTitleRow, panelTable.GetTextHeight(acTitleRow)
    comparisonTable.SetTextHeight acHeaderRow, panelTable.GetTextHeight(acHeaderRow)
    comparisonTable.SetTextHeight acDataRow, panelTable.GetTextHeight(acDataRow)
    
    ' Set column widths
    UpdateProgress progressFrm, "Setting table properties...", 55
    comparisonTable.SetColumnWidth 0, 50  ' ITEM
    comparisonTable.SetColumnWidth 1, 150 ' MANUFACTURER
    comparisonTable.SetColumnWidth 2, 150 ' PART NO
    comparisonTable.SetColumnWidth 3, 60  ' PANEL-QTY
    comparisonTable.SetColumnWidth 4, 60  ' SCHEM.-QTY
    comparisonTable.SetColumnWidth 5, 60  ' SLD-QTY (new column)
    comparisonTable.SetColumnWidth 6, 60  ' DIFFERENCE
    comparisonTable.SetColumnWidth 7, 200 ' NOTES
    comparisonTable.SetColumnWidth 8, 100 ' MANUAL ITEM CHECK
    
    ' Set title row
    comparisonTable.SetText 0, 0, "ITEM QTY COMPARISON"
    comparisonTable.MergeCells 0, 0, 0, 7 ' Merge title across all columns
    comparisonTable.SetAlignment 0, acMiddleCenter
    
    ' Set header row
    comparisonTable.SetText 1, 0, "ITEM"
    comparisonTable.SetText 1, 1, "MANUFACTURER"
    comparisonTable.SetText 1, 2, "PART NO."
    comparisonTable.SetText 1, 3, "PANEL-QTY"
    comparisonTable.SetText 1, 4, "SCHEM.-QTY"
    comparisonTable.SetText 1, 5, "SLD-QTY"
    comparisonTable.SetText 1, 6, "DIFFERENCE"
    comparisonTable.SetText 1, 7, "NOTES"
    comparisonTable.SetText 1, 8, "MANUAL CHECK"
    
    ' Rotate text in the header row for specified columns
    comparisonTable.SetTextRotation 1, 3, acDegrees090
    comparisonTable.SetTextRotation 1, 4, acDegrees090
    comparisonTable.SetTextRotation 1, 5, acDegrees090
    comparisonTable.SetTextRotation 1, 6, acDegrees090
    
    ' Adjust header row height to accommodate rotated text
    comparisonTable.SetRowHeight 1, 60
    
    ' Populate table with data
    UpdateProgress progressFrm, "Preparing data for table...", 60
    row = 2 ' Start at row 2 (after title and header)
    
    ' Convert allItems keys to an array for sorting
    Dim sortedItems() As String
    ReDim sortedItems(allItems.Count - 1)
    
    i = 0
    For Each currentItem In allItems.Keys
        sortedItems(i) = currentItem
        i = i + 1
    Next
    
    ' Simple bubble sort (for simplicity - can be improved)
    UpdateProgress progressFrm, "Sorting items...", 65
    Dim temp As String
    For i = LBound(sortedItems) To UBound(sortedItems) - 1
        For j = i + 1 To UBound(sortedItems)
            ' Try numeric comparison if both are numbers
            If IsNumeric(sortedItems(i)) And IsNumeric(sortedItems(j)) Then
                If CInt(sortedItems(i)) > CInt(sortedItems(j)) Then
                    temp = sortedItems(i)
                    sortedItems(i) = sortedItems(j)
                    sortedItems(j) = temp
                End If
            ElseIf sortedItems(i) > sortedItems(j) Then
                ' String comparison
                temp = sortedItems(i)
                sortedItems(i) = sortedItems(j)
                sortedItems(j) = temp
            End If
        Next j
    Next i
    
    ' Fill data in order
    UpdateProgress progressFrm, "Populating comparison table...", 70
    For i = LBound(sortedItems) To UBound(sortedItems)
        currentItem = sortedItems(i)
        
        ' Set ITEM
        comparisonTable.SetText row, 0, currentItem
        
        ' Get MANUFACTURER and PART NO.
        manufacturer = ""
        partNo = ""
        
        If panelItems.Exists(currentItem) Then
            Dim panelRow As Long
            panelRow = panelItems(currentItem)
            manufacturer = panelTable.GetText(panelRow, 1)
            partNo = panelTable.GetText(panelRow, 2)
        ElseIf schematicItems.Exists(currentItem) Then
            Dim schematicRow As Long
            schematicRow = schematicItems(currentItem)
            manufacturer = schematicTable.GetText(schematicRow, 1)
            partNo = schematicTable.GetText(schematicRow, 2)
        ElseIf sldItems.Exists(currentItem) Then
            Dim sldRow As Long
            sldRow = sldItems(currentItem)
            manufacturer = sldTable.GetText(sldRow, 1)
            partNo = sldTable.GetText(sldRow, 2)
        End If
        
        ' Set MANUFACTURER and PART NO.
        comparisonTable.SetText row, 1, manufacturer
        comparisonTable.SetText row, 2, partNo
        
        ' Set quantities
        panelQtyValue = 0
        schematicQtyValue = 0
        sldQtyValue = 0
        
        If panelQty.Exists(currentItem) Then
            panelQtyValue = panelQty(currentItem)
            comparisonTable.SetText row, 3, CStr(panelQtyValue)
        End If
        
        If schematicQty.Exists(currentItem) Then
            schematicQtyValue = schematicQty(currentItem)
            comparisonTable.SetText row, 4, CStr(schematicQtyValue)
        End If
        
        If sldQty.Exists(currentItem) Then
            sldQtyValue = sldQty(currentItem)
            comparisonTable.SetText row, 5, CStr(sldQtyValue)
        End If
        '*******
        ' Calculate difference using the new logic
        If schematicQtyValue = 0 Then
            difference = panelQtyValue - sldQtyValue
        ElseIf sldQtyValue = 0 Then
            difference = panelQtyValue - schematicQtyValue
        ElseIf panelQtyValue = sldQtyValue Then
            difference = panelQtyValue - schematicQtyValue
        ElseIf panelQtyValue = schematicQtyValue Then
            difference = panelQtyValue - sldQtyValue
        Else
            difference = panelQtyValue - schematicQtyValue
        End If
        ' Only show difference if it's not 0
        If difference <> 0 Then
            comparisonTable.SetText row, 6, CStr(difference)
        End If
        
        ' Apply coloring rule: If DIFFERENCE is non-empty and (SCHEMQTY or SLDQTY) is non-empty
        If difference <> 0 And (schematicQtyValue <> 0 Or sldQtyValue <> 0) Then
            ' Set background color
            Dim cellbgcol As New AcadAcCmColor
            On Error Resume Next
            cellbgcol.SetRGB 204, 0, 51  ' Equivalent to color 242
            comparisonTable.SetCellBackgroundColor row, 3, cellbgcol
            comparisonTable.SetCellBackgroundColor row, 4, cellbgcol
            comparisonTable.SetCellBackgroundColor row, 5, cellbgcol
            comparisonTable.SetCellBackgroundColor row, 6, cellbgcol
            On Error GoTo ErrorHandler
        End If
        
        ' NOTES column left blank
        
        row = row + 1
        
        ' Update progress periodically
        If i Mod 5 = 0 Then
            UpdateProgress progressFrm, "Populating table: " & i & " of " & UBound(sortedItems), 70 + (25 * i / UBound(sortedItems))
        End If
    Next i
    
    ' Update table and zoom to see it
    UpdateProgress progressFrm, "Finalizing table...", 95
    comparisonTable.Update
    acDoc.Application.ZoomExtents
    
    UpdateProgress progressFrm, "Process completed", 100
    
    MsgBox "Comparison table created successfully at coordinates (0,0).", vbInformation
    Unload progressFrm
    Exit Sub
    
ErrorHandler:
    MsgBox "An error occurred: " & Err.Number & " - " & Err.Description, vbExclamation, "Error"
    Unload progressFrm
End Sub

Sub Bomtools()
    frmBOM.show
End Sub

'—— in a normal VBA module ——
Public Function LoadCsvToDict(csvPath As String) As Object
    Dim fso As Object, ts As Object
    Dim line As String, fld As Variant
    Dim d   As Object

    Set fso = CreateObject("Scripting.FileSystemObject")
    If Not fso.FileExists(csvPath) Then
        MsgBox "CSV not found: " & csvPath, vbExclamation
        Exit Function
    End If

    Set ts = fso.OpenTextFile(csvPath, 1)   ' ForReading
    Set d = CreateObject("Scripting.Dictionary")

    ' Skip header
    If Not ts.AtEndOfStream Then ts.ReadLine

    Do While Not ts.AtEndOfStream
        line = ts.ReadLine
        fld = Split(line, ",")
        If UBound(fld) >= 2 Then
            ' fld(0)=P_ITEM, fld(1)=MFG, fld(2)=CAT, fld(3)=QTY
            d(fld(0)) = Array(fld(1), fld(2), fld(3))
        End If
    Loop

    ts.Close
    Set LoadCsvToDict = d
End Function

Sub ItemTools()
    frmCheckItems.show
End Sub
Sub TransferDINRailToBOM_DI()
    ' Variable declarations
    Dim acDoc As AcadDocument
    Dim dinTable As AcadTable
    Dim bomTable As AcadTable
    Dim pickPoint(0 To 2) As Double
    Dim entityName As AcadEntity
    Dim progressForm As Object
    Dim rowCount As Long
    Dim currentRow As Long
    Dim progressValue As Integer
    
    ' Constants
    Const SCALE_FACTOR As Double = 0.001  ' Convert mm to m
    Const DECIMAL_PLACES As Integer = 2   ' Round to 2 decimal places
    
    ' Column indices variables
    Dim dinMfgCol As Long
    Dim dinCatCol As Long
    Dim dinTotCol As Long
    Dim bomMfgCol As Long
    Dim bomPartCol As Long
    Dim bomQTYCol As Long
    
    ' Initialize objects to Nothing to help with error handling
    Set progressForm = Nothing
    
    ' Main code starts here
    On Error GoTo ErrorHandler
    
    ' Create progress form
    Set progressForm = New progressForm
    progressForm.show vbModeless
    Call UpdateProgress(progressForm, "Initializing...", 0)
    
    ' Get the active document
    Set acDoc = ThisDrawing
    
    Call UpdateProgress(progressForm, "Please select DIN RAIL SUMMARY table...", 5)
    
    ' Show clear instructions in a message box
    MsgBox "IMPORTANT: You will now be asked to select the DIN RAIL SUMMARY table." & vbCrLf & vbCrLf & _
           "• Click on the TABLE BORDER (the outline of the table)" & vbCrLf & _
           "• Do NOT click on text inside the table", _
           vbInformation, "Select DIN RAIL SUMMARY Table"
           
    ' Get DIN RAIL SUMMARY table
    On Error Resume Next
    ThisDrawing.Utility.GetEntity entityName, pickPoint, "Select the DIN RAIL SUMMARY table: "
    If Err.Number <> 0 Then
        MsgBox "Error selecting DIN RAIL SUMMARY table: " & Err.Description
        Unload progressForm
        Exit Sub
    End If
    On Error GoTo ErrorHandler
    
    If entityName Is Nothing Then
        MsgBox "No DIN RAIL SUMMARY table selected. Exiting macro."
        Unload progressForm
        Exit Sub
    End If
    
    If TypeOf entityName Is AcadTable Then
        Set dinTable = entityName
    Else
        MsgBox "Selected entity is not a table. Exiting macro."
        Unload progressForm
        Exit Sub
    End If
    
    Call UpdateProgress(progressForm, "Please select BOM table...", 15)
    
    ' Show clear instructions for BOM table selection
    MsgBox "IMPORTANT: You will now be asked to select the BOM table." & vbCrLf & vbCrLf & _
           "• Click on the TABLE BORDER (the outline of the table)" & vbCrLf & _
           "• Do NOT click on text inside the table", _
           vbInformation, "Select BOM Table"
    
    ' Get BOM table
    On Error Resume Next
    ThisDrawing.Utility.GetEntity entityName, pickPoint, "Select the BOM table: "
    If Err.Number <> 0 Then
        MsgBox "Error selecting BOM table: " & Err.Description
        Unload progressForm
        Exit Sub
    End If
    On Error GoTo ErrorHandler
    
    If entityName Is Nothing Then
        MsgBox "No BOM table selected. Exiting macro."
        Unload progressForm
        Exit Sub
    End If
    
    If TypeOf entityName Is AcadTable Then
        Set bomTable = entityName
    Else
        MsgBox "Selected entity is not a table. Exiting macro."
        Unload progressForm
        Exit Sub
    End If
    
    Call UpdateProgress(progressForm, "Analyzing table structure...", 20)
    
    ' Find required columns in DIN RAIL SUMMARY table
    dinMfgCol = -1
    dinCatCol = -1
    dinTotCol = -1
    For col = 0 To dinTable.Columns - 1
        Select Case UCase(Trim(dinTable.GetText(1, col)))
            Case "MFG"
                dinMfgCol = col
            Case "CAT"
                dinCatCol = col
            Case "TOTAL"
                dinTotCol = col
        End Select
    Next col
    
    Call UpdateProgress(progressForm, "Locating columns in BOM table...", 25)
    
    ' Find required columns in BOM table
    bomMfgCol = -1
    bomPartCol = -1
    bomQTYCol = -1
    For col = 0 To bomTable.Columns - 1
        Select Case UCase(Trim(bomTable.GetText(0, col)))
            Case "MANUFACTURER"
                bomMfgCol = col
            Case "CATALOGUE"
                bomPartCol = col
            Case "QTY"
                bomQTYCol = col
        End Select
    Next col
    
    ' Verify all required columns were found
    If dinMfgCol = -1 Or dinCatCol = -1 Or dinTotCol = -1 Then
        MsgBox "Could not find MFG, CAT or TOTAL columns in DIN RAIL SUMMARY table."
        Unload progressForm
        Exit Sub
    End If
    
    If bomMfgCol = -1 Or bomPartCol = -1 Or bomQTYCol = -1 Then
        MsgBox "Could not find MANUFACTURER, CATALOGUE or QTY columns in BOM table. "
        Exit Sub
    End If
    
    Call UpdateProgress(progressForm, "Preparing for data transfer...", 30)
    
    ' Start undo mark
    acDoc.StartUndoMark
    
    ' Get row count for progress calculation
    rowCount = bomTable.rows - 2 ' Exclude header row
    currentRow = 0
    
    ' Process each row in BOM table
    Dim bomRow As Long
    Dim dinRow As Long
    Dim locationCol As Long
    Dim sourceValue As Double
    Dim scaledValue As Double
    
    Call UpdateProgress(progressForm, "Transferring DIN rail data...", 35)
    
    ' Start from row 2 (after header)
    For bomRow = 2 To bomTable.rows - 1
        currentRow = currentRow + 1
        
        Dim bomMfg As String
        Dim bomPart As String
        bomMfg = Trim(bomTable.GetText(bomRow, bomMfgCol))
        bomPart = Trim(bomTable.GetText(bomRow, bomPartCol))
        
        ' Look for matching row in DIN RAIL SUMMARY
        For dinRow = 2 To dinTable.rows - 1
            Dim dinMfg As String
            Dim dinPart As String
            dinMfg = Trim(dinTable.GetText(dinRow, dinMfgCol))
            dinPart = Trim(dinTable.GetText(dinRow, dinCatCol))
            
            ' If match found, process location columns
            If dinMfg = bomMfg And dinPart = bomPart Then
                On Error Resume Next
                sourceValue = CDbl(dinTable.GetText(dinRow, dinTotCol))
                If Err.Number = 0 Then
                    ' Scale and round the value
                    scaledValue = Round(sourceValue * SCALE_FACTOR, DECIMAL_PLACES)
                    ' Format the value to always show 2 decimal places
                    bomTable.SetText bomRow, bomQTYCol, Format(scaledValue, "0.00")
                End If
                Exit For  ' Exit DIN row loop once match is found
            End If
        Next dinRow
        
        ' Update progress - scale from 35% to 95%
        progressValue = CInt(35 + (currentRow / rowCount) * 60)
        Call UpdateProgress(progressForm, "Transferring DIN rail data... (" & currentRow & " of " & rowCount & ")", progressValue)
    Next bomRow
    
    ' End undo mark
    acDoc.EndUndoMark
    
    ' Update the display
    acDoc.Regen True
    
    Call UpdateProgress(progressForm, "Transfer completed successfully!", 100)
    
    MsgBox "Transfer completed successfully!"
    Unload progressForm
    Exit Sub

ErrorHandler:
    ' Capture error info first
    Dim errDescription As String
    Dim errNumber As Long
    errDescription = Err.Description
    errNumber = Err.Number
    
    ' Safe cleanup - use On Error Resume Next for cleanup operations
    On Error Resume Next
    
    ' End undo mark if needed
    If Not acDoc Is Nothing Then
        acDoc.EndUndoMark  ' This may fail, but we'll continue
    End If
    
    ' Unload progress form if it exists
    If Not progressForm Is Nothing Then
        Unload progressForm  ' This may fail, but we'll continue
    End If
    
    ' Now report the original error
    If errNumber = 91 Then  ' Object not found error
        MsgBox "Error: Unable to process the tables. Please check that all columns contain valid data.", _
               vbCritical, "Error"
    Else
        MsgBox "An error occurred: " & errDescription & " (Error " & errNumber & ")", _
               vbCritical, "Error"
    End If
End Sub

Attribute VB_Name = "frmBOM"
Attribute VB_Base = "0{176294C5-C6B4-4B2D-9A86-FBED0C956F25}{0DCB6D0A-2810-462F-B5C3-0F2672AD417E}"
Attribute VB_GlobalNameSpace = False
Attribute VB_Creatable = False
Attribute VB_PredeclaredId = True
Attribute VB_Exposed = False
Attribute VB_TemplateDerived = False
Attribute VB_Customizable = False
Private Sub cmdBOM_Click()
    ConsolidateBOMNewTable
End Sub


Private Sub cmdInsert_Click()
    ThisDrawing.SendCommand ("CREATEDINSUMMARY" & vbCr)
End Sub

Private Sub cmdManufac_Click()
    UpdateSuppliers
End Sub

Private Sub cmdNotes_Click()
    UpdateNotes
End Sub

Private Sub cmdTransfer_Click()
    TransferDINRailToBOM
End Sub

Private Sub cmdTransfer2_Click()
    TransferDINRailToBOM_DI
End Sub

Attribute VB_Name = "frmBlockList"
Attribute VB_Base = "0{28D96E4D-247B-4FEB-8C3E-3B7294B8817F}{F7D7EA3A-D2C1-417F-B960-2FA69E461D84}"
Attribute VB_GlobalNameSpace = False
Attribute VB_Creatable = False
Attribute VB_PredeclaredId = True
Attribute VB_Exposed = False
Attribute VB_TemplateDerived = False
Attribute VB_Customizable = False
Private Sub lstBlocks_Click()
    Dim selectedBlockName As String
    selectedBlockName = Me.lstBlocks.Value
    ThisDrawing.SendCommand "SelectBlocksByName" & vbCr & selectedBlockName & vbCr
End Sub

Private Sub lstBlocks_DblClick(ByVal Cancel As MSForms.ReturnBoolean)
    Dim selectedBlockName As String
    selectedBlockName = Me.lstBlocks.Value
    ThisDrawing.SendCommand "ZoomToBlockByName" & vbCr & selectedBlockName & vbCr
End Sub

Private Sub UserForm_Initialize()
    Dim doc As AcadDocument
    Set doc = ThisDrawing

    Dim entity As AcadEntity
    Dim blockRef As AcadBlockReference
    Dim insertedBlockNames As New Collection
    Dim name As Variant

    On Error Resume Next ' Ignore errors in the collection (duplicates)
    For Each entity In doc.modelSpace
        If TypeOf entity Is AcadBlockReference Then
            Set blockRef = entity
            insertedBlockNames.Add blockRef.name, blockRef.name ' Use block name as the key to avoid duplicates
        End If
    Next entity
    On Error GoTo 0 ' Reset error handling

    For Each name In insertedBlockNames
        Me.lstBlocks.AddItem name
    Next name
End Sub

Attribute VB_Name = "frmChangeBlockFont"
Attribute VB_Base = "0{1FE0127E-AB6C-43B5-8E1E-126476249EF0}{8B1D3978-3556-4C11-B853-578AEF4CDBDF}"
Attribute VB_GlobalNameSpace = False
Attribute VB_Creatable = False
Attribute VB_PredeclaredId = True
Attribute VB_Exposed = False
Attribute VB_TemplateDerived = False
Attribute VB_Customizable = False
Private Sub cmdFontBlock_Click()
 If cmbFonts.Text <> "" Then
    ThisDrawing.SendCommand ("ChangeBlocksFont" & vbCr & cmbFonts.Text & vbCr)
 End If
End Sub

Private Sub cmdMleader_Click()
 If cmbFonts.Text <> "" Then
    ThisDrawing.SendCommand ("ChangeMLeaderFont" & vbCr & cmbFonts.Text & vbCr)
 End If
End Sub

Private Sub cmdText_Click()
 If cmbFonts.Text <> "" Then
    ThisDrawing.SendCommand ("ChangeTextFont" & vbCr & cmbFonts.Text & vbCr)
 End If
End Sub

Private Sub UserForm_Initialize()
    Dim i As Integer
    Dim textStyle As AcadTextStyle
    cmbFonts.Clear
    For Each textStyle In ThisDrawing.TextStyles
        cmbFonts.AddItem (textStyle.name)
    Next textStyle
End Sub

Attribute VB_Name = "frmCheckItems"
Attribute VB_Base = "0{AF48B8F6-3FB2-4E10-8908-2C48F1393061}{16F5DDC6-C75E-497E-B65F-57C273AC2DE8}"
Attribute VB_GlobalNameSpace = False
Attribute VB_Creatable = False
Attribute VB_PredeclaredId = True
Attribute VB_Exposed = False
Attribute VB_TemplateDerived = False
Attribute VB_Customizable = False
Private Sub cmdCompare_Click()
    Dim dict    As Object
    Dim csvPath As String
    Dim tblEnt  As AcadEntity
    Dim tbl      As AcadTable
    Dim pickPt   As Variant
    Dim key      As Variant
    Dim found    As Boolean
    Dim i        As Long
    Dim newRow As Integer
    Dim projName As String
    
    ' 1) Ask user for the CSV file path
    ThisDrawing.SendCommand "LoadActivePorjectName" & vbCr
    projName = ThisDrawing.GetVariable("USERS5")
    csvPath = ThisDrawing.GetVariable("TEMPPREFIX") & projName & "_QA-Itemlist.csv"
    '"C:\Users\user\AppData\Local\Temp\QA-Itemlist.csv"
    Set dict = LoadCsvToDict(csvPath)
    If dict Is Nothing Then Exit Sub

    ' 2) Prompt to pick your AutoCAD table
    On Error Resume Next
    ThisDrawing.Utility.GetEntity tblEnt, pickPt, _
      "Select the SCHEMATIC ITEM SUMMARY table: "
    If Err.Number <> 0 Or Not TypeOf tblEnt Is AcadTable Then
        MsgBox "Invalid selection or canceled.", vbExclamation
        Exit Sub
    End If
    On Error GoTo 0
    Set tbl = tblEnt

    ' 3) Clear ListBox and start comparing
    With Me.lstInvalid
        .Clear
        .ColumnCount = 4
    End With

    For Each key In dict.Keys
        found = False

        ' scan rows (skip header at row 0)
        For i = 1 To tbl.rows - 1
            If Trim(tbl.GetText(i, 0)) = CStr(key) Then
                found = True
                ' compare MFG(col1) & CAT(col2)
                If tbl.GetText(i, 1) <> dict(key)(0) _
                   Or tbl.GetText(i, 2) <> dict(key)(1) _
                   Or tbl.GetText(i, 3) <> dict(key)(2) Then
                    With lstInvalid
                        newRow = .ListCount
                        .AddItem
                        .List(newRow, 0) = CStr(key)
                        .List(newRow, 1) = dict(key)(0)
                        .List(newRow, 2) = dict(key)(1)
                        .List(newRow, 3) = dict(key)(2)
                    End With
                End If
                Exit For
            End If
        Next i

        ' if not found at all, also list it
        If Not found Then
            With lstInvalid
                newRow = .ListCount
                .AddItem
                .List(newRow, 0) = CStr(key)
                .List(newRow, 1) = dict(key)(0)
                .List(newRow, 2) = dict(key)(1)
            End With
        End If
    Next key

    ' 4) Update status label
    Me.lblStatus.Caption = Me.lstInvalid.ListCount & " mismatches found"
End Sub

Private Sub cmdItemSummary_Click()
    ThisDrawing.SendCommand "CreateQAItemSummary" & vbCr
End Sub

Private Sub cmdLoadItems_Click()
    ThisDrawing.SendCommand "QA-ItemListProject" & vbCr
End Sub

Private Sub cmdQABalloons_Click()
    ThisDrawing.SendCommand "QA-BalloonDiffProject" & vbCr
End Sub

Attribute VB_Name = "frmCopyDwg"
Attribute VB_Base = "0{1EC2364B-B35B-404F-B2E6-6398240D9C05}{6FE1926F-599C-4F85-9D34-91A32AFC9DA1}"
Attribute VB_GlobalNameSpace = False
Attribute VB_Creatable = False
Attribute VB_PredeclaredId = True
Attribute VB_Exposed = False
Attribute VB_TemplateDerived = False
Attribute VB_Customizable = False

Dim csvList As Collection
Dim SelCol As Integer
Dim SelCol1 As Integer
Dim SelCol2 As Integer
Dim SelCol3 As Integer
Dim SelCol4 As Integer
Dim SelCol5 As Integer
Dim SelCol6 As Integer
Dim SelCol7 As Integer
Dim SelCol8 As Integer

Private Sub cmdChangePLC_Click()
Dim find, replace, blockType, attr As String
find = txtFind.Text
replace = txtReplace.Text
blockType = "1"
attr = cmbPlcAttr.Text & txtNum.Text
ThisDrawing.SendCommand ("ReplaceAttrValByType" & vbCr & """" & find & """" & vbCr & """" & replace & """" & vbCr & blockType & vbCr & attr & vbCr)
End Sub

Private Sub cmdCopy_Click()
    Dim oldName, newName, desc1, desc2, desc3, sheet, section, subSec, folder As String
    Dim cmdStr As String
    oldName = txtOld.Text
    newName = txtNew.Text
    desc1 = txtDesc1.Text
    desc2 = txtDesc2.Text
    desc3 = txtDesc3.Text
    sheet = txtSht.Text
    section = txtSec.Text
    subSec = txtSub.Text
    folder = txtFolder.Text
    cmdStr = "(c:copy_project_drawing)" & vbCr & _
         """" & oldName & """" & vbCr & _
         """" & newName & """" & vbCr & _
         """" & desc1 & """" & vbCr & _
         """" & desc2 & """" & vbCr & _
         """" & desc3 & """" & vbCr & _
         """" & sheet & """" & vbCr & _
         """" & section & """" & vbCr & _
         """" & subSec & """" & vbCr & _
         """" & folder & """" & vbCr
    ThisDrawing.SendCommand cmdStr
    If (lstFindTags.ListIndex <> -1) And (chkProgress.Value) And (lstFindTags.ListIndex + 1 < lstFindTags.ListCount) Then
        lstFindTags.ListIndex = lstFindTags.ListIndex + 1
    End If
End Sub

Private Sub cmdLoadCSV_Click()
    Dim csvCols As Integer
    Dim isFirstRow As Boolean
    Dim opt As Control
    Dim csvPath As String
    Dim csvData As String
    Dim parts() As String
    Dim i As Long
    Dim itemToAdd() As String  ' Array to hold up to 5 columns
    ThisDrawing.SendCommand "GetCSVFilePath2" & vbCr
    csvPath = ThisDrawing.GetVariable("USERS2")
    ' Check if a CSV file path was actually retrieved
    If csvPath = "" Then
        MsgBox "No CSV file selected.", vbExclamation
        Exit Sub
    End If
    
    ' Initialize the FindReplaceList collection
    Set csvList = New Collection
    lstFindTags.Clear
    ' Open the CSV file and read its contents
    isFirstRow = True
    Open csvPath For Input As #1
    Do Until EOF(1)
        Line Input #1, csvData ' Read each line from the file
        parts = Split(csvData, ",") ' Split the line into parts using the comma as a delimiter
        ' Ensure there are at least two parts (find text and replace text)
        ' Reset the itemToAdd array
        If isFirstRow Then
            csvCols = UBound(parts) + 1
            isFirstRow = False
            ' Validate that we have at least one column
            If csvCols < 1 Then
                MsgBox "CSV file must contain at least one column.", vbExclamation
                Close #1
                Exit Sub
            End If
        End If
        ReDim itemToAdd(csvCols - 1)
        For i = 0 To (csvCols - 1)
            itemToAdd(i) = ""
        Next i
        
        ' Copy available values from the current row
        For i = 0 To UBound(parts)
            If i < csvCols Then
                itemToAdd(i) = parts(i)
            End If
        Next i
        
        ' Add to collection and listbox
        csvList.Add itemToAdd
        lstFindTags.AddItem parts(0)
    Loop
    Close #1
    If lstFindTags.ListCount > 0 Then
        lstFindTags.ListIndex = 0
        spnCol.Enabled = True
        spnCol1.Enabled = True
        spnCol2.Enabled = True
        spnCol3.Enabled = True
        spnCol4.Enabled = True
        'spnCol5.Enabled = True
        spnCol6.Enabled = True
        spnCol7.Enabled = True
        spnCol.Max = csvCols - 1
        spnCol1.Max = csvCols - 1
        spnCol2.Max = csvCols - 1
        spnCol3.Max = csvCols - 1
        spnCol4.Max = csvCols - 1
        'spnCol5.Max = csvCols - 1
        spnCol6.Max = csvCols - 1
        spnCol7.Max = csvCols - 1
        spnCol.Value = 0
        spnCol1.Value = 0
        spnCol2.Value = 0
        spnCol3.Value = 0
        spnCol4.Value = 0
        'spnCol5.Value = 0
        spnCol6.Value = 0
        spnCol7.Value = 0
        lblCol.Caption = spnCol.Value
        lblCol1.Caption = spnCol1.Value
        lblCol2.Caption = spnCol1.Value
        lblCol3.Caption = spnCol1.Value
        lblCol4.Caption = spnCol1.Value
        'lblCol5.Caption = spnCol1.Value
        lblCol6.Caption = spnCol1.Value
        lblCol7.Caption = spnCol1.Value
        SelCol = 0
        SelCol1 = 0
        SelCol2 = 0
        SelCol3 = 0
        SelCol4 = 0
        'SelCol5 = 0
        SelCol6 = 0
        SelCol7 = 0
        txtOld.Text = csvList(lstFindTags.ListIndex + 1)(SelCol)
        txtNew.Text = csvList(lstFindTags.ListIndex + 1)(SelCol1)
        txtDesc1.Text = csvList(lstFindTags.ListIndex + 1)(SelCol2)
        txtDesc2.Text = csvList(lstFindTags.ListIndex + 1)(SelCol3)
        txtDesc3.Text = csvList(lstFindTags.ListIndex + 1)(SelCol4)
        txtSht.Text = csvList(lstFindTags.ListIndex + 1)(SelCol5)
        txtSec.Text = csvList(lstFindTags.ListIndex + 1)(SelCol6)
        txtSub.Text = csvList(lstFindTags.ListIndex + 1)(SelCol7)
    End If
End Sub

Private Sub cmdReplace_Click()
Dim find, replace As String
find = txtFind.Text
replace = txtReplace.Text
ThisDrawing.SendCommand ("ReplaceTagValContd" & vbCr & """" & find & """" & vbCr & """" & replace & """" & vbCr)
If (lstFindTags.ListIndex <> -1) And (chkProgress.Value) And (lstFindTags.ListIndex + 1 < lstFindTags.ListCount) Then
    lstFindTags.ListIndex = lstFindTags.ListIndex + 1
End If
End Sub

Private Sub cmdSelectAttr_Click()
Dim find, replace, blockType, attr As String
find = txtFind.Text
replace = txtReplace.Text
attr = cmbAttrname.Text
ThisDrawing.SendCommand ("ReplaceAttrValContd" & vbCr & """" & find & """" & vbCr & """" & replace & """" & vbCr & attr & vbCr)
If (lstFindTags.ListIndex <> -1) And (chkProgress.Value) And (lstFindTags.ListIndex + 1 < lstFindTags.ListCount) Then
    lstFindTags.ListIndex = lstFindTags.ListIndex + 1
End If
End Sub

Private Sub cmdText_Click()
Dim find, replace, blockType As String
find = txtFind.Text
replace = txtReplace.Text
ThisDrawing.SendCommand ("FindReplaceTextMTextContd" & vbCr & """" & find & """" & vbCr & """" & replace & """" & vbCr)
If (lstFindTags.ListIndex <> -1) And (chkProgress.Value) And (lstFindTags.ListIndex + 1 < lstFindTags.ListCount) Then
    lstFindTags.ListIndex = lstFindTags.ListIndex + 1
End If
End Sub

Private Sub cmdUpdate_Click()
    Dim oldName, newName, desc1, desc2, desc3, sheet, section, subSec, folder As String
    Dim cmdStr As String
    oldName = txtOld.Text
    newName = txtNew.Text
    desc1 = txtDesc1.Text
    desc2 = txtDesc2.Text
    desc3 = txtDesc3.Text
    sheet = txtSht.Text
    section = txtSec.Text
    subSec = txtSub.Text
    folder = txtFolder.Text
    cmdStr = "(c:update_project_drawing)" & vbCr & _
         """" & oldName & """" & vbCr & _
         """" & desc1 & """" & vbCr & _
         """" & desc2 & """" & vbCr & _
         """" & desc3 & """" & vbCr & _
         """" & sheet & """" & vbCr & _
         """" & section & """" & vbCr & _
         """" & subSec & """" & vbCr & _
         """" & folder & """" & vbCr
    ThisDrawing.SendCommand cmdStr
    If (lstFindTags.ListIndex <> -1) And (chkProgress.Value) And (lstFindTags.ListIndex + 1 < lstFindTags.ListCount) Then
        lstFindTags.ListIndex = lstFindTags.ListIndex + 1
    End If
End Sub

Private Sub cmdUpdateDesc_Click()
    Dim oldName, newName, desc1, desc2, desc3, sheet, section, subSec, folder As String
    Dim cmdStr As String
    oldName = txtOld.Text
    newName = txtNew.Text
    desc1 = txtDesc1.Text
    desc2 = txtDesc2.Text
    desc3 = txtDesc3.Text
    sheet = txtSht.Text
    section = txtSec.Text
    subSec = txtSub.Text
    folder = txtFolder.Text
    cmdStr = "(c:wdp_update_descriptions)" & vbCr & _
         """" & desc1 & """" & vbCr & _
         """" & desc2 & """" & vbCr & _
         """" & desc3 & """" & vbCr
    ThisDrawing.SendCommand cmdStr
End Sub

Private Sub cmdUpdateSec_Click()
    Dim oldName, newName, desc1, desc2, desc3, sheet, section, subSec, folder As String
    Dim cmdStr As String
    oldName = txtOld.Text
    newName = txtNew.Text
    desc1 = txtDesc1.Text
    desc2 = txtDesc2.Text
    desc3 = txtDesc3.Text
    sheet = txtSht.Text
    section = txtSec.Text
    subSec = txtSub.Text
    folder = txtFolder.Text
    cmdStr = "(c:wdp_update_sections)" & vbCr & _
         """" & section & """" & vbCr & _
         """" & subSec & """" & vbCr
    ThisDrawing.SendCommand cmdStr
End Sub

Private Sub Label1_Click()

End Sub

Private Sub lblCol_Click()

End Sub

Private Sub lstFindTags_Change()

End Sub

Private Sub lstFindTags_Click()
    If Not chkFixOld.Value Then
        txtOld.Text = csvList(lstFindTags.ListIndex + 1)(SelCol)
    End If
    txtNew.Text = csvList(lstFindTags.ListIndex + 1)(SelCol1)
    If Not chkFixDesc.Value Then
        txtDesc1.Text = csvList(lstFindTags.ListIndex + 1)(SelCol2)
        txtDesc2.Text = csvList(lstFindTags.ListIndex + 1)(SelCol3)
        txtDesc3.Text = csvList(lstFindTags.ListIndex + 1)(SelCol4)
    End If
    'txtSht.Text = csvList(lstFindTags.ListIndex + 1)(SelCol5)
    If Not chkFixSec.Value Then
        txtSec.Text = csvList(lstFindTags.ListIndex + 1)(SelCol6)
    End If
    If Not chkFixSub.Value Then
        txtSub.Text = csvList(lstFindTags.ListIndex + 1)(SelCol7)
    End If
End Sub

Private Sub Opt1_Click()
    SelCol = 0
    txtReplace.Text = csvList(lstFindTags.ListIndex + 1)(SelCol)
End Sub

Private Sub Opt2_Click()
    SelCol = 1
    txtOld.Text = csvList(lstFindTags.ListIndex + 1)(SelCol)
End Sub

Private Sub Opt3_Click()
    SelCol = 2
    txtReplace.Text = csvList(lstFindTags.ListIndex + 1)(SelCol)
End Sub

Private Sub Opt4_Click()
    SelCol = 3
    txtReplace.Text = csvList(lstFindTags.ListIndex + 1)(SelCol)
End Sub

Private Sub Opt5_Click()
    SelCol = 4
    txtReplace.Text = csvList(lstFindTags.ListIndex + 1)(SelCol)
End Sub

Private Sub spn1_Change()
     txtNum.Text = Format$(spn1.Value, "00")
End Sub

Private Sub spnCol_Change()
    lblCol.Caption = spnCol.Value
    SelCol = spnCol.Value
    txtOld.Text = csvList(lstFindTags.ListIndex + 1)(SelCol)
End Sub

Private Sub txtNum_Exit(ByVal Cancel As MSForms.ReturnBoolean)
    spn1.Value = txtNum.Value
End Sub

Private Sub spnCol1_Change()
    lblCol1.Caption = spnCol1.Value
    SelCol1 = spnCol1.Value
    txtNew.Text = csvList(lstFindTags.ListIndex + 1)(SelCol1)
End Sub

Private Sub spnCol2_Change()
    lblCol2.Caption = spnCol2.Value
    SelCol2 = spnCol2.Value
    txtDesc1.Text = csvList(lstFindTags.ListIndex + 1)(SelCol2)
End Sub

Private Sub spnCol3_Change()
    lblCol3.Caption = spnCol3.Value
    SelCol3 = spnCol3.Value
    txtDesc2.Text = csvList(lstFindTags.ListIndex + 1)(SelCol3)
End Sub

Private Sub spnCol4_Change()
    lblCol4.Caption = spnCol4.Value
    SelCol4 = spnCol4.Value
    txtDesc3.Text = csvList(lstFindTags.ListIndex + 1)(SelCol4)
End Sub

Private Sub spnCol5_Change()
    lblCol5.Caption = spnCol5.Value
    SelCol5 = spnCol5.Value
    txtSht.Text = csvList(lstFindTags.ListIndex + 1)(SelCol5)
End Sub

Private Sub spnCol6_Change()
    lblCol6.Caption = spnCol6.Value
    SelCol6 = spnCol6.Value
    txtSec.Text = csvList(lstFindTags.ListIndex + 1)(SelCol6)
End Sub

Private Sub spnCol7_Change()
    lblCol7.Caption = spnCol7.Value
    SelCol7 = spnCol7.Value
    txtSub.Text = csvList(lstFindTags.ListIndex + 1)(SelCol7)
End Sub

Private Sub spnCol8_Change()
    lblCol8.Caption = spnCol8.Value
    SelCol8 = spnCol8.Value
    txtFolder.Text = csvList(lstFindTags.ListIndex + 1)(SelCol8)
End Sub

Private Sub txtOld_Change()

End Sub

Private Sub txtSht_Change()

End Sub

Private Sub txtSub_Change()

End Sub

Private Sub UserForm_Initialize()
    spnCol1.Enabled = False
    spnCol2.Enabled = False
    spnCol3.Enabled = False
    spnCol4.Enabled = False
    spnCol5.Enabled = False
    spnCol6.Enabled = False
    spnCol7.Enabled = False
End Sub

Attribute VB_Name = "frmCountEq"
Attribute VB_Base = "0{7A0C74B7-7699-4214-918A-B996E8126C8E}{7BB65BA1-88C1-49BC-ACF1-36C91C05BED4}"
Attribute VB_GlobalNameSpace = False
Attribute VB_Creatable = False
Attribute VB_PredeclaredId = True
Attribute VB_Exposed = False
Attribute VB_TemplateDerived = False
Attribute VB_Customizable = False
Private Sub cmdCount_Click()
 ThisDrawing.SendCommand ("FindMLeaderWithTextRange" & vbCr & txtcount.Text & vbCr)
 Me.Hide
End Sub

Private Sub UserForm_Click()

End Sub

Attribute VB_Name = "frmInsertTag"
Attribute VB_Base = "0{E682B7E8-837C-4F82-B6E8-4D9ED640F9A4}{6CE7CE9D-0072-4178-B7A4-DE152689DB44}"
Attribute VB_GlobalNameSpace = False
Attribute VB_Creatable = False
Attribute VB_PredeclaredId = True
Attribute VB_Exposed = False
Attribute VB_TemplateDerived = False
Attribute VB_Customizable = False
Dim csvList As Collection
Dim SelCol As Integer
Private Sub cmdChangePLC_Click()
    Dim insert, replace, blockType, attr As String
    insert = txtPrefix.Text & txtInsert.Text & txtSuffix.Text
    blockType = "1"
    attr = cmbPlcAttr.Text & txtNum.Text
    ThisDrawing.SendCommand ("InsertAttrValContd" & vbCr & """" & insert & """" & vbCr & attr & vbCr)
End Sub

Private Sub cmdLoadCSV_Click()
    Dim csvCols As Integer
    Dim isFirstRow As Boolean
    Dim opt As Control
    Dim csvPath As String
    Dim csvData As String
    Dim parts() As String
    Dim i As Long
    Dim itemToAdd() As String  ' Array to hold up to 5 columns
    ThisDrawing.SendCommand "GetCSVFilePath2" & vbCr
    csvPath = ThisDrawing.GetVariable("USERS2")
    ' Check if a CSV file path was actually retrieved
    If csvPath = "" Then
        MsgBox "No CSV file selected.", vbExclamation
        Exit Sub
    End If
    
    ' Initialize the FindReplaceList collection
    Set csvList = New Collection
    lstFindTags.Clear
    ' Open the CSV file and read its contents
    isFirstRow = True
    Open csvPath For Input As #1
    Do Until EOF(1)
        Line Input #1, csvData ' Read each line from the file
        parts = Split(csvData, ",") ' Split the line into parts using the comma as a delimiter
        ' Ensure there are at least two parts (find text and replace text)
        ' Reset the itemToAdd array
        If isFirstRow Then
            csvCols = UBound(parts) + 1
            isFirstRow = False
            ' Validate that we have at least one column
            If csvCols < 1 Then
                MsgBox "CSV file must contain at least one column.", vbExclamation
                Close #1
                Exit Sub
            End If
        End If
        ReDim itemToAdd(csvCols - 1)
        For i = 0 To (csvCols - 1)
            itemToAdd(i) = ""
        Next i
        
        ' Copy available values from the current row
        For i = 0 To UBound(parts)
            If i < csvCols Then
                itemToAdd(i) = parts(i)
            End If
        Next i
        
        ' Add to collection and listbox
        csvList.Add itemToAdd
        lstFindTags.AddItem parts(0)
    Loop
    Close #1
    If lstFindTags.ListCount > 0 Then
        lstFindTags.ListIndex = 0
        spnCol.Enabled = True
        spnCol.Max = csvCols - 1
        spnCol.Value = 0
        lblCol.Caption = spnCol.Value
        SelCol = 0
        txtInsert.Text = csvList(lstFindTags.ListIndex + 1)(SelCol)
    End If
End Sub

Private Sub cmdReplace_Click()
Dim insert, replace As String
insert = txtPrefix.Text & txtInsert.Text & txtSuffix.Text
ThisDrawing.SendCommand ("InsertTagValContd" & vbCr & """" & insert & """" & vbCr)
If (lstFindTags.ListIndex <> -1) And (chkProgress.Value) And (lstFindTags.ListIndex + 1 < lstFindTags.ListCount) Then
    lstFindTags.ListIndex = lstFindTags.ListIndex + 1
End If
End Sub

Private Sub cmdSelectAttr_Click()
Dim insert, replace, blockType, attr As String
insert = txtPrefix.Text & txtInsert.Text & txtSuffix.Text
attr = cmbAttrname.Text
ThisDrawing.SendCommand ("InsertAttrValContd" & vbCr & """" & insert & """" & vbCr & attr & vbCr)
If (lstFindTags.ListIndex <> -1) And (chkProgress.Value) And (lstFindTags.ListIndex + 1 < lstFindTags.ListCount) Then
    lstFindTags.ListIndex = lstFindTags.ListIndex + 1
End If
End Sub

Private Sub cmdText_Click()
Dim insert, replace, blockType As String
insert = txtPrefix.Text & txtInsert.Text & txtSuffix.Text
ThisDrawing.SendCommand ("InsertTextMTextContd" & vbCr & """" & insert & """" & vbCr)
If (lstFindTags.ListIndex <> -1) And (chkProgress.Value) And (lstFindTags.ListIndex + 1 < lstFindTags.ListCount) Then
    lstFindTags.ListIndex = lstFindTags.ListIndex + 1
End If
End Sub

Private Sub cmdTrms_Click()
Dim insert, replace, blockType As String
insert = txtPrefix.Text & txtInsert.Text & txtSuffix.Text
blockType = "7"
ThisDrawing.SendCommand ("ChangeTagValByType" & vbCr & """" & insert & """" & vbCr & blockType & vbCr)
If (lstFindTags.ListIndex <> -1) And (chkProgress.Value) And (lstFindTags.ListIndex + 1 < lstFindTags.ListCount) Then
    lstFindTags.ListIndex = lstFindTags.ListIndex + 1
End If
End Sub

Private Sub CommandButton1_Click()

End Sub

Private Sub cmdXdata_Click()
Dim insert, replace, blockType, attr As String
insert = txtPrefix.Text & txtInsert.Text & txtSuffix.Text
attr = cmbAttrname.Text
ThisDrawing.SendCommand ("InsertPnlAttrValContd" & vbCr & """" & insert & """" & vbCr & attr & vbCr)
If (lstFindTags.ListIndex <> -1) And (chkProgress.Value) And (lstFindTags.ListIndex + 1 < lstFindTags.ListCount) Then
    lstFindTags.ListIndex = lstFindTags.ListIndex + 1
End If
End Sub

Private Sub lstFindTags_Click()
If lstFindTags.ListIndex > -1 Then
    txtInsert.Text = csvList(lstFindTags.ListIndex + 1)(SelCol)
End If
End Sub

Private Sub Opt1_Click()
SelCol = 0
txtInsert.Text = csvList(lstFindTags.ListIndex + 1)(SelCol)
End Sub

Private Sub Opt2_Click()
SelCol = 1
txtInsert.Text = csvList(lstFindTags.ListIndex + 1)(SelCol)
End Sub

Private Sub Opt3_Click()
SelCol = 2
txtInsert.Text = csvList(lstFindTags.ListIndex + 1)(SelCol)
End Sub

Private Sub Opt4_Click()
SelCol = 3
txtInsert.Text = csvList(lstFindTags.ListIndex + 1)(SelCol)
End Sub

Private Sub Opt5_Click()
SelCol = 4
txtInsert.Text = csvList(lstFindTags.ListIndex + 1)(SelCol)
End Sub

Private Sub spn1_Change()
     txtNum.Text = Format$(spn1.Value, "00")
End Sub
Private Sub spnCol_Change()
lblCol.Caption = spnCol.Value
SelCol = spnCol.Value
txtInsert.Text = csvList(lstFindTags.ListIndex + 1)(SelCol)
End Sub

Private Sub txtInsert_Change()

End Sub

Private Sub txtNum_Exit(ByVal Cancel As MSForms.ReturnBoolean)
    spn1.Value = txtNum.Value
End Sub

Private Sub UserForm_Initialize()
    Dim opt As Control
    SelCol = 0
    With Me.cmbAttrname
        .AddItem "DESC1"
        .AddItem "DESC2"
        .AddItem "DESC3"
        .AddItem "INST"
        .AddItem "LOC"
        .AddItem "CONTACT"
        .AddItem "P_TAGSTRIP"
        .AddItem "TAGSTRIP"
        .AddItem "P_TAG1"
        .AddItem "RATING1"
        .AddItem "RATING2"
        .AddItem "RATING3"
        .AddItem "TERM01"
        .AddItem "TERM"
        .AddItem "WDBLKNAM"
        .AddItem "L01WIREPERC"
    End With
    With Me.cmbPlcAttr
        .AddItem "DESCA"
        .AddItem "DESCB"
        .AddItem "DESCC"
        .AddItem "DESCD"
        .AddItem "DESCE"
    End With
    spnCol.Enabled = False
    
End Sub

Attribute VB_Name = "frmItemCount"
Attribute VB_Base = "0{F2F187AC-A2B3-4DE6-ACDE-FB6C603E35B6}{80CBAE8A-32CF-49D6-9DDC-C9A7F3730514}"
Attribute VB_GlobalNameSpace = False
Attribute VB_Creatable = False
Attribute VB_PredeclaredId = True
Attribute VB_Exposed = False
Attribute VB_TemplateDerived = False
Attribute VB_Customizable = False
Private Sub cmdClear_Click()
    lstCount.Clear
End Sub

Private Sub cmdCount_Click()
    Dim countValue, MFG, CAT As String
    Dim newRow As Integer
    MFG = txtMfg.Text
    CAT = txtCat.Text
    ThisDrawing.SendCommand "CountDwgMfgCat" & vbCr & MFG & vbCr & CAT & vbCr
    ' Get the USERI3 environment variable value
    countValue = ThisDrawing.GetVariable("USERI3")
    ' Display the value in a message box
    With lstCount
        newRow = .ListCount
        .AddItem
        .List(newRow, 0) = MFG
        .List(newRow, 1) = CAT
        .List(newRow, 2) = countValue
    End With
End Sub


Private Sub cmdPnlCount_Click()
    Dim countValue, MFG, CAT As String
    Dim newRow As Integer
    MFG = txtMfg.Text
    CAT = txtCat.Text
    ThisDrawing.SendCommand "CountPnlMfgCat" & vbCr & MFG & vbCr & CAT & vbCr
    ' Get the USERI3 environment variable value
    countValue = ThisDrawing.GetVariable("USERI3")
    ' Display the value in a message box
    With lstCount
        newRow = .ListCount
        .AddItem
        .List(newRow, 0) = MFG
        .List(newRow, 1) = CAT
        .List(newRow, 2) = countValue
    End With
End Sub

Private Sub UserForm_Initialize()

End Sub

Attribute VB_Name = "frmMulticat"
Attribute VB_Base = "0{ADF5C1AC-C78C-4C3A-9474-EA3EDE91AEC3}{53F88E75-0B3B-4C0B-A8F5-092A96B82F30}"
Attribute VB_GlobalNameSpace = False
Attribute VB_Creatable = False
Attribute VB_PredeclaredId = True
Attribute VB_Exposed = False
Attribute VB_TemplateDerived = False
Attribute VB_Customizable = False
Private Sub btnInsert_Click()
Dim MFG(5) As String
Dim CAT(5) As String
Dim csvMfg()
csvMfg = Array("MFG", "MFG01", "MFG02", "MFG03", "MFG04", "MFG05")
Dim csvCat()
csvCat = Array("CAT", "CAT01", "CAT02", "CAT03", "CAT04", "CAT05")
Dim csvChk(5) As Boolean
Dim C As Control
Dim i, j, k, n As Integer
Dim strAttrib, strVal As String
For Each C In Me.Controls
    If TypeName(C) = "TextBox" Then
        If Left(C.name, 6) = "txtMFG" Then
            i = CInt(Right(C.name, 1))
            MFG(i) = C.Text
        End If
        If Left(C.name, 6) = "txtCAT" Then
            j = CInt(Right(C.name, 1))
            CAT(j) = C.Text
        End If
    End If
    If TypeName(C) = "CheckBox" Then
        If Left(C.name, 3) = "chk" Then
            k = CInt(Right(C.name, 1))
            csvChk(k) = C.Value
        End If
    End If
Next C
strAttrib = ""
strVal = ""
For n = 0 To 5
    If csvChk(n) Then
        strAttrib = strAttrib + csvMfg(n) + "," + csvCat(n) + ","
        strVal = strVal + MFG(n) + "," + CAT(n) + ","
    End If
Next n
If strAttrib <> "" Then
    strAttrib = Left(strAttrib, Len(strAttrib) - 1)
    strVal = Left(strVal, Len(strVal) - 1)
Else
    Exit Sub
End If
ThisDrawing.SendCommand ("InsertMultiAttrValContd" & vbCr & strAttrib & vbCr & strVal & vbCr)
End Sub

Private Sub btnPanel_Click()
Dim MFG(5) As String
Dim CAT(5) As String
Dim csvMfg()
csvMfg = Array("MFG", "MFG01", "MFG02", "MFG03", "MFG04", "MFG05")
Dim csvCat()
csvCat = Array("CAT", "CAT01", "CAT02", "CAT03", "CAT04", "CAT05")
Dim csvChk(5) As Boolean
Dim C As Control
Dim i, j, k, n As Integer
Dim strAttrib, strVal As String
For Each C In Me.Controls
    If TypeName(C) = "TextBox" Then
        If Left(C.name, 6) = "txtMFG" Then
            i = CInt(Right(C.name, 1))
            MFG(i) = C.Text
        End If
        If Left(C.name, 6) = "txtCAT" Then
            j = CInt(Right(C.name, 1))
            CAT(j) = C.Text
        End If
    End If
    If TypeName(C) = "CheckBox" Then
        If Left(C.name, 3) = "chk" Then
            k = CInt(Right(C.name, 1))
            csvChk(k) = C.Value
        End If
    End If
Next C
strAttrib = ""
strVal = ""
For n = 0 To 5
    If csvChk(n) Then
        strAttrib = strAttrib + csvMfg(n) + "," + csvCat(n) + ","
        strVal = strVal + MFG(n) + "," + CAT(n) + ","
    End If
Next n
If strAttrib <> "" Then
    strAttrib = Left(strAttrib, Len(strAttrib) - 1)
    strVal = Left(strVal, Len(strVal) - 1)
Else
    Exit Sub
End If
ThisDrawing.SendCommand ("InsertMultiPnlValContd" & vbCr & strAttrib & vbCr & strVal & vbCr)
End Sub

Private Sub cmdClearOneline_Click()
    Dim insert, replace, blockType, attr As String
    insert = ""
    attr = "WDTYPE"
    ThisDrawing.SendCommand ("InsertAttrValContd" & vbCr & """" & insert & """" & vbCr & attr & vbCr)
End Sub

Private Sub cmdSetOneline_Click()
    Dim insert, replace, blockType, attr As String
    insert = "1-"
    attr = "WDTYPE"
    ThisDrawing.SendCommand ("InsertAttrValContd" & vbCr & """" & insert & """" & vbCr & attr & vbCr)
End Sub

Attribute VB_Name = "frmNewWireLayers"
Attribute VB_Base = "0{8DC6A6D5-0E06-45CB-AA40-9DB75F812096}{BD8C3B4B-0981-4E02-B0B0-AC4DA859CBAD}"
Attribute VB_GlobalNameSpace = False
Attribute VB_Creatable = False
Attribute VB_PredeclaredId = True
Attribute VB_Exposed = False
Attribute VB_TemplateDerived = False
Attribute VB_Customizable = False
Private Sub cmdOther_Click()
    ThisDrawing.SendCommand ("CreateNewWireLayerNoNum" & vbCr & "CTRL_NO_NUMBER" & vbCr)
    ThisDrawing.SendCommand ("CreateNewWireLayer" & vbCr & "CTRL_NUMBERED" & vbCr)
End Sub



Private Sub cmdProcess_Click()
    Dim startVal, endVal, prefix, layerName As String
    Dim numDigits, startNum, endNum, i As Integer
    startVal = txtFrom.Text
    endVal = txtTo.Text
    prefix = txtPrefix.Text
    If Not (IsNumeric(startVal) And IsNumeric(endVal)) Then
        MsgBox "Please enter a valid number."
        Exit Sub
    End If
    numDigits = Len(startVal)
    startNum = CInt(startVal)
    endNum = CInt(endVal)
    For i = startNum To endNum
        layerName = prefix & Format(i, String(numDigits, "0"))
        ThisDrawing.SendCommand ("CreateNewWireLayer" & vbCr & layerName & vbCr)
        ThisDrawing.Utility.Prompt ("Layer " & layerName & " Created" & vbCrLf)
        Sleep 20
    Next i
End Sub

Attribute VB_Name = "frmPLCDesc"
Attribute VB_Base = "0{88E470EC-6935-4EA3-AA19-F74A74A92544}{76C9A0BB-97E6-4F74-81FA-554017E8DD78}"
Attribute VB_GlobalNameSpace = False
Attribute VB_Creatable = False
Attribute VB_PredeclaredId = True
Attribute VB_Exposed = False
Attribute VB_TemplateDerived = False
Attribute VB_Customizable = False
Dim terminal As Integer
Dim PLCDesc As Collection
Dim skipTerm() As Integer
Dim csvList As Collection
Dim SelCol As Integer
Sub Terminal_UP()
    Dim item As Variant
    terminal = Val(txtTerm.Text)
    terminal = terminal + 1
    For Each item In skipTerm
    If terminal = item Then
        terminal = terminal + 1
    End If
    Next item
    txtTerm.Text = Format$(terminal, "00")
End Sub
Sub Terminal_Down()
    Dim item As Variant
    terminal = Val(txtTerm.Text)
    If terminal = 0 Then
        Exit Sub
    End If
    terminal = terminal - 1
    For Each item In skipTerm
    If terminal = item Then
        terminal = terminal - 1
    End If
    Next item
    txtTerm.Text = Format$(terminal, "00")
End Sub
Sub Terminal_Load()
    terminal = Val(txtTerm.Text)
    txtTerm.Text = Format$(terminal, "00")
End Sub

Private Sub cmbType_Change()
    'Dim e As Variant
    'Dim i As Integer
    'Terminal_Load
    'For Each e In PLCDesc
    '    If e(0) = cmbType.Text Then
    '       txtDescB.Text = e(2)
    '        txtDescC.Text = e(3)
    '        txtDescD.Text = e(4)
    '        txtDescE.Text = e(5)
    '    End If
    'Next e
End Sub

Private Sub cmdAI_Click()
 txtSkip.Text = "0,2,3,4,6,7,8,10,11,12,14,15,16,18,19,20,22,23,24,26,27,28"
 InitSkip
End Sub

Private Sub cmdAO_Click()

End Sub

Private Sub cmdClear_Click()
    Terminal_Load
    ThisDrawing.SendCommand "ChangeAttrValByType" & vbCr & "" & vbCr & 1 & vbCr & "DESCA" & Format$(terminal, "00") & vbCr
    ThisDrawing.SendCommand "ChangeAttrValByType" & vbCr & "" & vbCr & 1 & vbCr & "DESCB" & Format$(terminal, "00") & vbCr
    ThisDrawing.SendCommand "ChangeAttrValByType" & vbCr & "" & vbCr & 1 & vbCr & "DESCC" & Format$(terminal, "00") & vbCr
    ThisDrawing.SendCommand "ChangeAttrValByType" & vbCr & "" & vbCr & 1 & vbCr & "DESCD" & Format$(terminal, "00") & vbCr
    ThisDrawing.SendCommand "ChangeAttrValByType" & vbCr & "" & vbCr & 1 & vbCr & "DESCE" & Format$(terminal, "00") & vbCr
End Sub

Private Sub cmdDI_Click()
 txtSkip.Text = "1,10,19,28"
 InitSkip
End Sub

Private Sub cmdDO_Click()
 txtSkip.Text = "0,1,18,19"
 InitSkip
End Sub

Private Sub cmdDown_Click()
    Terminal_Down
End Sub

Private Sub cmdInsert_Click()
    Dim e As Variant
    Dim i As Integer
    Terminal_Load
    For Each e In PLCDesc
        If e(0) = cmbType.Text Then
            ThisDrawing.SendCommand "ChangeAttrValByType" & vbCr & """" & txtDesc.Text & """" & vbCr & 1 & vbCr & "DESCA" & Format$(terminal, "00") & vbCr
            ThisDrawing.SendCommand "ChangeAttrValByType" & vbCr & """" & e(2) & """" & vbCr & 1 & vbCr & "DESCB" & Format$(terminal, "00") & vbCr
            ThisDrawing.SendCommand "ChangeAttrValByType" & vbCr & """" & e(3) & """" & vbCr & 1 & vbCr & "DESCC" & Format$(terminal, "00") & vbCr
            ThisDrawing.SendCommand "ChangeAttrValByType" & vbCr & """" & e(4) & """" & vbCr & 1 & vbCr & "DESCD" & Format$(terminal, "00") & vbCr
            ThisDrawing.SendCommand "ChangeAttrValByType" & vbCr & """" & e(5) & """" & vbCr & 1 & vbCr & "DESCE" & Format$(terminal, "00") & vbCr
            Terminal_UP
        End If
    Next e
    If (lstFindTags.ListIndex <> -1) And (lstFindTags.ListIndex + 1 < lstFindTags.ListCount) Then
        lstFindTags.ListIndex = lstFindTags.ListIndex + 1
    End If
End Sub

Private Sub cmdLoadCSV_Click()
    Dim csvCols As Integer
    Dim isFirstRow As Boolean
    Dim opt As Control
    Dim csvPath As String
    Dim csvData As String
    Dim parts() As String
    Dim i As Long
    Dim itemToAdd() As String  ' Array to hold up to 5 columns
    ThisDrawing.SendCommand "GetCSVFilePath2" & vbCr
    csvPath = ThisDrawing.GetVariable("USERS2")
    ' Check if a CSV file path was actually retrieved
    If csvPath = "" Then
        MsgBox "No CSV file selected.", vbExclamation
        Exit Sub
    End If
    
    ' Initialize the FindReplaceList collection
    Set csvList = New Collection
    lstFindTags.Clear
    ' Open the CSV file and read its contents
    isFirstRow = True
    Open csvPath For Input As #1
    Do Until EOF(1)
        Line Input #1, csvData ' Read each line from the file
        parts = Split(csvData, ",") ' Split the line into parts using the comma as a delimiter
        ' Ensure there are at least two parts (find text and replace text)
        ' Reset the itemToAdd array
        If isFirstRow Then
            csvCols = UBound(parts) + 1
            isFirstRow = False
            ' Validate that we have at least one column
            If csvCols < 1 Then
                MsgBox "CSV file must contain at least one column.", vbExclamation
                Close #1
                Exit Sub
            End If
        End If
        ReDim itemToAdd(csvCols - 1)
        For i = 0 To (csvCols - 1)
            itemToAdd(i) = ""
        Next i
        
        ' Copy available values from the current row
        For i = 0 To UBound(parts)
            If i < csvCols Then
                itemToAdd(i) = parts(i)
            End If
        Next i
        
        ' Add to collection and listbox
        csvList.Add itemToAdd
        lstFindTags.AddItem parts(0)
    Loop
    Close #1
    If lstFindTags.ListCount > 0 Then
        lstFindTags.ListIndex = 0
        spnCol.Enabled = True
        spnCol.Max = csvCols - 1
        spnCol.Value = 0
        lblCol.Caption = spnCol.Value
        SelCol = 0
        txtDesc.Text = csvList(lstFindTags.ListIndex + 1)(SelCol)
    End If
End Sub

Private Sub cmdSet_Click()
Dim counter As Integer
    InitSkip
End Sub

Private Sub cmdShiftDescriptions_Click()
    Dim terminalNumber As String
    Dim wordCount As Integer
    Terminal_Load
    ' Get the terminal number from your form or use current terminal value
    terminalNumber = Format$(terminal, "00")
    
    ' Get the number of words to move from a text box or set directly
    wordCount = CInt(txtWordCount.Text) ' Assume you have a text box for this
    
    ' Call the AutoLISP function using SendCommand
    ThisDrawing.SendCommand "ShiftPLCDescriptions" & vbCr & _
                           terminalNumber & vbCr & _
                           CStr(wordCount) & vbCr
    Terminal_UP
    ' Update UI as needed
    If (lstFindTags.ListIndex <> -1) And (lstFindTags.ListIndex + 1 < lstFindTags.ListCount) Then
        lstFindTags.ListIndex = lstFindTags.ListIndex + 1
    End If
End Sub

Private Sub cmdTxtxInsert_Click()
    Terminal_Load
    ThisDrawing.SendCommand "ChangeAttrValByType" & vbCr & """" & txtDesc.Text & """" & vbCr & 1 & vbCr & "DESCA" & Format$(terminal, "00") & vbCr
    ThisDrawing.SendCommand "ChangeAttrValByType" & vbCr & """" & txtDescB.Text & """" & vbCr & 1 & vbCr & "DESCB" & Format$(terminal, "00") & vbCr
    ThisDrawing.SendCommand "ChangeAttrValByType" & vbCr & """" & txtDescC.Text & """" & vbCr & 1 & vbCr & "DESCC" & Format$(terminal, "00") & vbCr
    ThisDrawing.SendCommand "ChangeAttrValByType" & vbCr & """" & txtDescD.Text & """" & vbCr & 1 & vbCr & "DESCD" & Format$(terminal, "00") & vbCr
    ThisDrawing.SendCommand "ChangeAttrValByType" & vbCr & """" & txtDescE.Text & """" & vbCr & 1 & vbCr & "DESCE" & Format$(terminal, "00") & vbCr
    Terminal_UP
    If (lstFindTags.ListIndex <> -1) And (lstFindTags.ListIndex + 1 < lstFindTags.ListCount) Then
        lstFindTags.ListIndex = lstFindTags.ListIndex + 1
    End If
End Sub

Private Sub cmdUP_Click()
    Terminal_UP
End Sub

Sub InitSkip()
    Dim Values() As String
    Dim i As Integer
    Values = Split(txtSkip.Text, ",")
    ReDim skipTerm(0 To UBound(Values))
    For i = LBound(Values) To UBound(Values)
        skipTerm(i) = CInt(Values(i))
    Next i
End Sub

Private Sub Label10_Click()

End Sub

Private Sub Label7_Click()

End Sub

Private Sub lstFindTags_Change()

End Sub

Private Sub lstFindTags_Click()
If lstFindTags.ListIndex > -1 Then
    txtDesc.Text = csvList(lstFindTags.ListIndex + 1)(SelCol)
End If
End Sub

Private Sub Opt1_Click()
SelCol = 0
txtDesc.Text = csvList(lstFindTags.ListIndex + 1)(SelCol)
End Sub

Private Sub Opt2_Click()
SelCol = 1
txtDesc.Text = csvList(lstFindTags.ListIndex + 1)(SelCol)
End Sub

Private Sub Opt3_Click()
SelCol = 2
txtDesc.Text = csvList(lstFindTags.ListIndex + 1)(SelCol)
End Sub

Private Sub Opt4_Click()
SelCol = 3
txtDesc.Text = csvList(lstFindTags.ListIndex + 1)(SelCol)
End Sub

Private Sub Opt5_Click()
SelCol = 4
txtDesc.Text = csvList(lstFindTags.ListIndex + 1)(SelCol)
End Sub

Private Sub spnCol_Change()
    lblCol.Caption = spnCol.Value
    SelCol = spnCol.Value
    txtDesc.Text = csvList(lstFindTags.ListIndex + 1)(SelCol)
End Sub

Private Sub txtDesc_Change()

End Sub

Private Sub UserForm_Initialize()
Dim csvPath As String
Dim csvData As String
Dim parts() As String
InitSkip
Terminal_Load
' Initialize the FindReplaceList collection
Set PLCDesc = New Collection
csvPath = "C:\Users\USER\Documents\ACADE_VBA\PLCDef.csv"
Open csvPath For Input As #1
Do Until EOF(1)
    Line Input #1, csvData ' Read each line from the file
    parts = Split(csvData, ",") ' Split the line into parts using the comma as a delimiter
    If UBound(parts) = 5 Then
        PLCDesc.Add Array(parts(0), parts(1), parts(2), parts(3), parts(4), parts(5)) ' Add the pair to the list
        If parts(1) = 0 Then
            cmbType.AddItem parts(0)
        End If
    End If
Loop
Close #1
spnCol.Enabled = False
End Sub

Attribute VB_Name = "frmPinlist"
Attribute VB_Base = "0{169539D4-032C-4C03-9228-723F378B2319}{BADAF236-808D-4ECA-A426-E1D1F243512E}"
Attribute VB_GlobalNameSpace = False
Attribute VB_Creatable = False
Attribute VB_PredeclaredId = True
Attribute VB_Exposed = False
Attribute VB_TemplateDerived = False
Attribute VB_Customizable = False
Option Explicit

Private Const CSV_PATH As String = "C:\Users\user\Documents\ACADE_VBA\Pinlist.csv"




Private Sub UserForm_Initialize()
    LoadPinlistData
End Sub

Private Sub LoadPinlistData()
    Dim fso As Object
    Dim ts As Object
    Dim line As String
    Dim parts() As String
    
    lstRecords.Clear
    
    'Create folder if it doesn't exist
    Set fso = CreateObject("Scripting.FileSystemObject")
    If Not fso.FolderExists("C:\Users\user\Documents\ACADE_VBA") Then
        fso.CreateFolder "C:\Users\user\Documents\ACADE_VBA"
    End If
    
    'Create file if it doesn't exist
    If Not fso.FileExists(CSV_PATH) Then
        Set ts = fso.CreateTextFile(CSV_PATH, True)
        ts.Close
    End If
    
    'Read CSV file and populate listbox
    Set ts = fso.OpenTextFile(CSV_PATH, 1) 'ForReading = 1
    
    Do While Not ts.AtEndOfStream
        line = ts.ReadLine
        If Len(line) > 0 Then
            parts = Split(line, ",", 3) 'Split into max 3 parts
            If UBound(parts) >= 0 Then
                lstRecords.AddItem replace(parts(0), """", "") 'Add description to listbox
            End If
        End If
    Loop
    
    ts.Close
    Set ts = Nothing
    Set fso = Nothing
End Sub

Private Sub lstRecords_Click()
    Dim fso As Object
    Dim ts As Object
    Dim line As String
    Dim parts() As String
    
    If lstRecords.ListIndex < 0 Then Exit Sub
    
    Set fso = CreateObject("Scripting.FileSystemObject")
    Set ts = fso.OpenTextFile(CSV_PATH, 1)
    
    'Find the selected record
    Do While Not ts.AtEndOfStream
        line = ts.ReadLine
        parts = Split(line, ",", 3)
        If UBound(parts) >= 2 Then
            If parts(0) = ("""" & lstRecords.Text & """") Then
                txtDesc.Text = replace(parts(0), """", "")
                txtBlock.Text = replace(parts(1), """", "")
                txtPinlist.Text = replace(parts(2), """", "")
                Exit Do
            End If
        End If
    Loop
    
    ts.Close
    Set ts = Nothing
    Set fso = Nothing
End Sub

Private Sub cmdSave_Click()
    Dim fso As Object
    Dim ts As Object
    Dim newLine As String
    
    'Validate inputs
    If Len(Trim(txtDesc.Text)) = 0 Or Len(Trim(txtBlock.Text)) = 0 Or Len(Trim(txtPinlist.Text)) = 0 Then
        MsgBox "Please fill in all fields!", vbExclamation
        Exit Sub
    End If
    
    'Format new line with quotes
    newLine = """" & txtDesc.Text & """,""" & txtBlock.Text & """,""" & txtPinlist.Text & """"
    
    'Append to file
    Set fso = CreateObject("Scripting.FileSystemObject")
    Set ts = fso.OpenTextFile(CSV_PATH, 8) 'ForAppending = 8
    
    ts.WriteLine newLine
    
    ts.Close
    Set ts = Nothing
    Set fso = Nothing
    
    'Reload list
    LoadPinlistData
    
    'Clear fields
    txtDesc.Text = ""
    txtBlock.Text = ""
    txtPinlist.Text = ""
    
    MsgBox "Pinlist saved successfully!", vbInformation
End Sub

Private Sub cmdInsert_Click()
    Dim acadApp As Object
    Dim csvString As String
    
    'Validate selection
    If Len(Trim(txtDesc.Text)) = 0 Or Len(Trim(txtBlock.Text)) = 0 Or Len(Trim(txtPinlist.Text)) = 0 Then
        MsgBox "Please select a record or fill in all fields!", vbExclamation
        Exit Sub
    End If
    
    'Format CSV string for AutoLISP
    csvString = txtDesc.Text & "," & txtBlock.Text & "," & txtPinlist.Text
    
    'Run AutoLISP command
    Set acadApp = GetObject(, "AutoCAD.Application")
    acadApp.ActiveDocument.SendCommand "PinlistCSVUpd" & vbCr & """" & csvString & """" & vbCr
    
    Set acadApp = Nothing
End Sub

Attribute VB_Name = "frmReplaceTag"
Attribute VB_Base = "0{50A31585-C22F-4DAE-9F05-62396BD36670}{EF8095E9-7628-4906-B63D-E8760AD6E06A}"
Attribute VB_GlobalNameSpace = False
Attribute VB_Creatable = False
Attribute VB_PredeclaredId = True
Attribute VB_Exposed = False
Attribute VB_TemplateDerived = False
Attribute VB_Customizable = False
Dim csvList As Collection
Dim SelCol As Integer

Private Sub cmdChangePLC_Click()
Dim find, replace, blockType, attr As String
find = txtFind.Text
replace = txtReplace.Text
blockType = "1"
attr = cmbPlcAttr.Text & txtNum.Text
ThisDrawing.SendCommand ("ReplaceAttrValByType" & vbCr & """" & find & """" & vbCr & """" & replace & """" & vbCr & blockType & vbCr & attr & vbCr)
End Sub

Private Sub cmdLoadCSV_Click()
    Dim csvCols As Integer
    Dim isFirstRow As Boolean
    Dim opt As Control
    Dim csvPath As String
    Dim csvData As String
    Dim parts() As String
    Dim i As Long
    Dim itemToAdd() As String  ' Array to hold up to 5 columns
    ThisDrawing.SendCommand "GetCSVFilePath2" & vbCr
    csvPath = ThisDrawing.GetVariable("USERS2")
    ' Check if a CSV file path was actually retrieved
    If csvPath = "" Then
        MsgBox "No CSV file selected.", vbExclamation
        Exit Sub
    End If
    
    ' Initialize the FindReplaceList collection
    Set csvList = New Collection
    lstFindTags.Clear
    ' Open the CSV file and read its contents
    isFirstRow = True
    Open csvPath For Input As #1
    Do Until EOF(1)
        Line Input #1, csvData ' Read each line from the file
        parts = Split(csvData, ",") ' Split the line into parts using the comma as a delimiter
        ' Ensure there are at least two parts (find text and replace text)
        ' Reset the itemToAdd array
        If isFirstRow Then
            csvCols = UBound(parts) + 1
            isFirstRow = False
            ' Validate that we have at least one column
            If csvCols < 1 Then
                MsgBox "CSV file must contain at least one column.", vbExclamation
                Close #1
                Exit Sub
            End If
        End If
        ReDim itemToAdd(csvCols - 1)
        For i = 0 To (csvCols - 1)
            itemToAdd(i) = ""
        Next i
        
        ' Copy available values from the current row
        For i = 0 To UBound(parts)
            If i < csvCols Then
                itemToAdd(i) = parts(i)
            End If
        Next i
        
        ' Add to collection and listbox
        csvList.Add itemToAdd
        lstFindTags.AddItem parts(0)
    Loop
    Close #1
    If lstFindTags.ListCount > 0 Then
        lstFindTags.ListIndex = 0
        spnCol.Enabled = True
        spnCol.Max = csvCols - 1
        spnCol.Value = 0
        lblCol.Caption = spnCol.Value
        SelCol = 0
        txtReplace.Text = csvList(lstFindTags.ListIndex + 1)(SelCol)
    End If
End Sub

Private Sub cmdReplace_Click()
Dim find, replace As String
find = txtFind.Text
replace = txtReplace.Text
ThisDrawing.SendCommand ("ReplaceTagValContd" & vbCr & """" & find & """" & vbCr & """" & replace & """" & vbCr)
If (lstFindTags.ListIndex <> -1) And (chkProgress.Value) And (lstFindTags.ListIndex + 1 < lstFindTags.ListCount) Then
    lstFindTags.ListIndex = lstFindTags.ListIndex + 1
End If
End Sub

Private Sub cmdSelectAttr_Click()
Dim find, replace, blockType, attr As String
find = txtFind.Text
replace = txtReplace.Text
attr = cmbAttrname.Text
ThisDrawing.SendCommand ("ReplaceAttrValContd" & vbCr & """" & find & """" & vbCr & """" & replace & """" & vbCr & attr & vbCr)
If (lstFindTags.ListIndex <> -1) And (chkProgress.Value) And (lstFindTags.ListIndex + 1 < lstFindTags.ListCount) Then
    lstFindTags.ListIndex = lstFindTags.ListIndex + 1
End If
End Sub

Private Sub cmdSelectPnl_Click()
Dim find, replace, blockType, attr As String
find = txtFind.Text
replace = txtReplace.Text
attr = cmbAttrname.Text
ThisDrawing.SendCommand ("ReplacePnlAttrValContd" & vbCr & """" & find & """" & vbCr & """" & replace & """" & vbCr & attr & vbCr)
If (lstFindTags.ListIndex <> -1) And (chkProgress.Value) And (lstFindTags.ListIndex + 1 < lstFindTags.ListCount) Then
    lstFindTags.ListIndex = lstFindTags.ListIndex + 1
End If
End Sub

Private Sub cmdText_Click()
Dim find, replace, blockType As String
find = txtFind.Text
replace = txtReplace.Text
ThisDrawing.SendCommand ("FindReplaceTextMTextContd" & vbCr & """" & find & """" & vbCr & """" & replace & """" & vbCr)
If (lstFindTags.ListIndex <> -1) And (chkProgress.Value) And (lstFindTags.ListIndex + 1 < lstFindTags.ListCount) Then
    lstFindTags.ListIndex = lstFindTags.ListIndex + 1
End If
End Sub

Private Sub lstFindTags_Click()
    txtReplace.Text = csvList(lstFindTags.ListIndex + 1)(SelCol)
End Sub

Private Sub Opt1_Click()
    SelCol = 0
    txtReplace.Text = csvList(lstFindTags.ListIndex + 1)(SelCol)
End Sub

Private Sub Opt2_Click()
    SelCol = 1
    txtReplace.Text = csvList(lstFindTags.ListIndex + 1)(SelCol)
End Sub

Private Sub Opt3_Click()
    SelCol = 2
    txtReplace.Text = csvList(lstFindTags.ListIndex + 1)(SelCol)
End Sub

Private Sub Opt4_Click()
    SelCol = 3
    txtReplace.Text = csvList(lstFindTags.ListIndex + 1)(SelCol)
End Sub

Private Sub Opt5_Click()
    SelCol = 4
    txtReplace.Text = csvList(lstFindTags.ListIndex + 1)(SelCol)
End Sub

Private Sub spn1_Change()
     txtNum.Text = Format$(spn1.Value, "00")
End Sub

Private Sub spnCol_Change()
    lblCol.Caption = spnCol.Value
    SelCol = spnCol.Value
    txtReplace.Text = csvList(lstFindTags.ListIndex + 1)(SelCol)
End Sub

Private Sub txtNum_Exit(ByVal Cancel As MSForms.ReturnBoolean)
    spn1.Value = txtNum.Value
End Sub

Private Sub UserForm_Initialize()
    Dim opt As Control
    SelCol = 0
    With Me.cmbAttrname
        .AddItem "DESC1"
        .AddItem "DESC2"
        .AddItem "DESC3"
        .AddItem "LOC"
        .AddItem "CONTACT"
        .AddItem "P_TAGSTRIP"
        .AddItem "P_TAG1"
        .AddItem "WIRENO"
        .AddItem "WIRENOF"
    End With
    With Me.cmbPlcAttr
        .AddItem "DESCA"
        .AddItem "DESCB"
        .AddItem "DESCC"
    End With
    spnCol.Enabled = False
End Sub

Attribute VB_Name = "frmReplaceTagCSV"
Attribute VB_Base = "0{C0717F71-4965-4C20-887F-4879844A53A4}{C9D6F6CD-2952-4C9B-BB54-70B8EB2E38E2}"
Attribute VB_GlobalNameSpace = False
Attribute VB_Creatable = False
Attribute VB_PredeclaredId = True
Attribute VB_Exposed = False
Attribute VB_TemplateDerived = False
Attribute VB_Customizable = False
' Global variable to store find/replace pairs
Dim FindReplaceList As Collection
Private Sub cmdLoadCSV_Click()
Dim csvPath As String
Dim csvData As String
Dim parts() As String
ThisDrawing.SendCommand "GetCSVFilePath" & vbCr
csvPath = ThisDrawing.GetVariable("USERS1")
' Check if a CSV file path was actually retrieved
If csvPath = "" Then
    MsgBox "No CSV file selected.", vbExclamation
    Exit Sub
End If

' Initialize the FindReplaceList collection
Set FindReplaceList = New Collection
lstFindTags.Clear
' Open the CSV file and read its contents
Open csvPath For Input As #1
Do Until EOF(1)
    Line Input #1, csvData ' Read each line from the file
    parts = Split(csvData, ",") ' Split the line into parts using the comma as a delimiter
    
    ' Ensure there are at least two parts (find text and replace text)
    If UBound(parts) >= 1 Then
        FindReplaceList.Add Array(parts(0), parts(1)) ' Add the pair to the list
        lstFindTags.AddItem parts(0)
    End If
Loop
Close #1
End Sub
Private Sub cmdChild_Click()
Dim find, replace, blockType As String
find = txtFind.Text
replace = txtReplace.Text
blockType = "5"
ThisDrawing.SendCommand ("ReplaceTagValByType" & vbCr & """" & find & """" & vbCr & """" & replace & """" & vbCr & blockType & vbCr)
End Sub

Private Sub cmdDesc1_Click()
Dim find, replace, blockType As String
find = txtFind.Text
replace = txtReplace.Text
ThisDrawing.SendCommand ("ReplaceAttrVal" & vbCr & """" & find & """" & vbCr & """" & replace & """" & vbCr & "DESC1" & vbCr)
End Sub

Private Sub cmdDesc2_Click()
Dim find, replace, blockType As String
find = txtFind.Text
replace = txtReplace.Text
ThisDrawing.SendCommand ("ReplaceAttrVal" & vbCr & """" & find & """" & vbCr & """" & replace & """" & vbCr & "DESC2" & vbCr)
End Sub

Private Sub cmdDesc3_Click()
Dim find, replace, blockType As String
find = txtFind.Text
replace = txtReplace.Text
ThisDrawing.SendCommand ("ReplaceAttrVal" & vbCr & """" & find & """" & vbCr & """" & replace & """" & vbCr & "DESC3" & vbCr)
End Sub

Private Sub cmdPar_Click()
Dim find, replace, blockType As String
find = txtFind.Text
replace = txtReplace.Text
blockType = "4"
ThisDrawing.SendCommand ("ReplaceTagValByType" & vbCr & """" & find & """" & vbCr & """" & replace & """" & vbCr & blockType & vbCr)
End Sub

Private Sub cmdReplace_Click()
Dim find, replace As String
find = txtFind.Text
replace = txtReplace.Text
ThisDrawing.SendCommand ("ReplaceTagVal" & vbCr & find & vbCr & replace & vbCr)
End Sub
Private Sub cmdplc_Click()
Dim find, replace, blockType As String
find = txtFind.Text
replace = txtReplace.Text
blockType = "1"
ThisDrawing.SendCommand ("ReplaceTagValByType" & vbCr & """" & find & """" & vbCr & """" & replace & """" & vbCr & blockType & vbCr)
End Sub

Private Sub cmdplcdescA_Click()
Dim find, replace, blockType, numAttr As String
find = txtFind.Text
replace = txtReplace.Text
numAttr = txtnumPlcAttr.Text
blockType = "1"
ThisDrawing.SendCommand ("ReplaceMultipleAttrValsByType" & vbCr & """" & find & """" & vbCr & """" & replace & """" & vbCr & blockType & vbCr & "DESCA" & vbCr & numAttr & vbCr)
End Sub

Private Sub cmdplcsedcB_Click()
Dim find, replace, blockType, numAttr As String
find = txtFind.Text
replace = txtReplace.Text
numAttr = txtnumPlcAttr.Text
blockType = "1"
ThisDrawing.SendCommand ("ReplaceMultipleAttrValsByType" & vbCr & """" & find & """" & vbCr & """" & replace & """" & vbCr & blockType & vbCr & "DESCB" & vbCr & numAttr & vbCr)
End Sub

Private Sub cmdPtag_Click()
Dim find, replace, blockType As String
find = txtFind.Text
replace = txtReplace.Text
ThisDrawing.SendCommand ("ReplaceAttrVal" & vbCr & """" & find & """" & vbCr & """" & replace & """" & vbCr & "P_TAG1" & vbCr)
End Sub

Private Sub cmdPtagStrip_Click()
Dim find, replace, blockType As String
find = txtFind.Text
replace = txtReplace.Text
ThisDrawing.SendCommand ("ReplaceAttrVal" & vbCr & """" & find & """" & vbCr & """" & replace & """" & vbCr & "P_TAGSTRIP" & vbCr)
End Sub

Private Sub cmdTerm_Click()
Dim find, replace, blockType As String
find = txtFind.Text
replace = txtReplace.Text
blockType = "7"
ThisDrawing.SendCommand ("ReplaceTagValByType" & vbCr & """" & find & """" & vbCr & """" & replace & """" & vbCr & blockType & vbCr)
End Sub

Private Sub cmdTermLoc_Click()
Dim find, replace, blockType As String
find = txtFind.Text
replace = txtReplace.Text
blockType = "7"
ThisDrawing.SendCommand ("ReplaceAttrValByType" & vbCr & """" & find & """" & vbCr & """" & replace & """" & vbCr & blockType & vbCr & "LOC" & vbCr)
End Sub

Private Sub cmdText_Click()
Dim find, replace, blockType As String
find = txtFind.Text
replace = txtReplace.Text
ThisDrawing.SendCommand ("FindReplaceTextMText" & vbCr & """" & find & """" & vbCr & """" & replace & """" & vbCr)
End Sub

Private Sub cmdWireno_Click()
Dim find, replace, blockType As String
find = txtFind.Text
replace = txtReplace.Text
blockType = "2"
ThisDrawing.SendCommand ("ReplaceAttrValByType" & vbCr & """" & find & """" & vbCr & """" & replace & """" & vbCr & blockType & vbCr & "WIRENO" & vbCr)
End Sub

Private Sub cmdWireNoFix_Click()
Dim find, replace, blockType As String
find = txtFind.Text
replace = txtReplace.Text
blockType = "2"
ThisDrawing.SendCommand ("ReplaceAttrValByType" & vbCr & """" & find & """" & vbCr & """" & replace & """" & vbCr & blockType & vbCr & "WIRENOF" & vbCr)
End Sub


Private Sub Frame1_Click()

End Sub

Private Sub lstFindTags_Click()
txtFind.Text = lstFindTags.Value
txtReplace.Text = FindReplaceList.item(lstFindTags.ListIndex + 1)(1)
End Sub

Private Sub UserForm_Initialize()
Set FindReplaceList = New Collection
End Sub

Attribute VB_Name = "frmSequencer"
Attribute VB_Base = "0{3A046AF1-0A4C-4BD9-B754-A596C99328B5}{2A34D7BD-96A4-4215-9678-4241B273220E}"
Attribute VB_GlobalNameSpace = False
Attribute VB_Creatable = False
Attribute VB_PredeclaredId = True
Attribute VB_Exposed = False
Attribute VB_TemplateDerived = False
Attribute VB_Customizable = False
Private Sub cmdRenumber_Click()
    Dim start, incr, prefix, suffix As String
    start = txtStart.Text
    incr = txtIncrement.Text
    prefix = txtPrefix.Text
    suffix = txtSuffix.Text
    ThisDrawing.SendCommand "UpdateTextSequence" & vbCr & start & vbCr & incr & vbCr & """" & prefix & """" & vbCr & """" & suffix & """" & vbCr
End Sub

Private Sub cmdRenumberAttr_Click()
    Dim start, incr, prefix, suffix, attr As String
    attr = cmbAttrname.Text
    start = txtStart.Text
    incr = txtIncrement.Text
    prefix = txtPrefix.Text
    suffix = txtSuffix.Text
    ThisDrawing.SendCommand "ResequenceAttributes" & vbCr & """" & attr & """" & vbCr & """" & prefix & """" & vbCr & """" & suffix & """" & vbCr & start & vbCr & incr & vbCr
End Sub

Private Sub cmdRenumberTags_Click()
    Dim start, incr, prefix, suffix As String
    start = txtStart.Text
    incr = txtIncrement.Text
    prefix = txtPrefix.Text
    suffix = txtSuffix.Text
    ThisDrawing.SendCommand "ResequenceTags" & vbCr & """" & prefix & """" & vbCr & """" & suffix & """" & vbCr & start & vbCr & incr & vbCr
End Sub

Private Sub UserForm_Click()

End Sub

Private Sub UserForm_Initialize()
    With Me.cmbAttrname
        .AddItem "DESC1"
        .AddItem "DESC2"
        .AddItem "DESC3"
        .AddItem "INST"
        .AddItem "LOC"
        .AddItem "CONTACT"
        .AddItem "P_TAGSTRIP"
        .AddItem "P_TAG1"
        .AddItem "RATING1"
        .AddItem "RATING2"
        .AddItem "WIRENO"
        .AddItem "WIRENOF"
        .AddItem "TERM01"
        .AddItem "SIGCODE"
    End With
End Sub

Attribute VB_Name = "frmSubsecTag"
Attribute VB_Base = "0{4DFF16FD-D9B3-49B6-961B-94A70BB472C2}{DC57AF4D-821B-419B-94FA-B39CA5358918}"
Attribute VB_GlobalNameSpace = False
Attribute VB_Creatable = False
Attribute VB_PredeclaredId = True
Attribute VB_Exposed = False
Attribute VB_TemplateDerived = False
Attribute VB_Customizable = False
Dim blockType As Integer

Private Sub cmbType_Change()
    Select Case cmbType.Text
        Case "TERMINALS"
            blockType = 7
        Case "PARENT"
            blockType = 4
        Case "CHILD"
            blockType = 5
        Case "REF ARROW"
            blockType = 8
    End Select
End Sub

Private Sub cmdInsertAttr_Click()
    Dim find, prefix, suffix, attr As String
    find = txtFind.Text
    prefix = txtPrefix.Text
    suffix = txtSuffix.Text
    attr = cmbAttrname.Text
    Dim cmd As String
    cmd = "(c:ChangeAttrValBySubsec)" & vbCr & _
          """" & prefix & """" & vbCr & _
          """" & suffix & """" & vbCr & _
          CStr(blockType) & vbCr & _
          """" & attrName & """" & vbCr
    
    ' Send the command to AutoCAD
    ThisDrawing.SendCommand cmd
End Sub

Private Sub cmdInsertTag_Click()
    Dim find, prefix, suffix, attr As String
    find = txtFind.Text
    prefix = txtPrefix.Text
    suffix = txtSuffix.Text
    attr = cmbAttrname.Text
    Dim cmd As String
    cmd = "(c:ChangeTagValBySubsec)" & vbCr & _
          """" & prefix & """" & vbCr & _
          """" & suffix & """" & vbCr & _
          CStr(blockType) & vbCr
    
    ' Send the command to AutoCAD
    ThisDrawing.SendCommand cmd
End Sub

Private Sub cmdReplaceAttr_Click()
    Dim find, prefix, suffix, attr As String
    find = txtFind.Text
    prefix = txtPrefix.Text
    suffix = txtSuffix.Text
    attr = cmbAttrname.Text
        Dim cmd As String
    cmd = "(c:ReplaceAttrValBySubsec)" & vbCr & _
          """" & find & """" & vbCr & _
          CStr(blockType) & vbCr & _
          """" & attrName & """" & vbCr
    
    ' Send the command to AutoCAD
    ThisDrawing.SendCommand cmd
End Sub

Private Sub cmdReplaceTag_Click()
    Dim find, prefix, suffix, attr As String
    find = txtFind.Text
    prefix = txtPrefix.Text
    suffix = txtSuffix.Text
    attr = cmbAttrname.Text
    Dim cmd As String
    cmd = "(c:ReplaceTagValBySubsec)" & vbCr & _
          """" & find & """" & vbCr & _
          CStr(blockType) & vbCr
    
    ' Send the command to AutoCAD
    ThisDrawing.SendCommand cmd
End Sub

Private Sub UserForm_Initialize()
    With Me.cmbAttrname
        .AddItem "DESC1"
        .AddItem "DESC2"
        .AddItem "DESC3"
        .AddItem "INST"
        .AddItem "LOC"
        .AddItem "CONTACT"
        .AddItem "P_TAGSTRIP"
        .AddItem "P_TAG1"
        .AddItem "RATING1"
        .AddItem "RATING2"
        .Text = "DESC1"
    End With
    With Me.cmbType
        .AddItem "TERMINALS"
        .AddItem "PARENT"
        .AddItem "CHILD"
        .AddItem "REF ARROW"
        .Text = "TERMINALS"
    End With
    blockType = 7
End Sub

Attribute VB_Name = "frmTextMtext"
Attribute VB_Base = "0{F1F5DD1C-9A4D-4C59-A8B6-6037D1A89444}{A2C8E2E3-04E2-4586-A9F0-777F2523C56C}"
Attribute VB_GlobalNameSpace = False
Attribute VB_Creatable = False
Attribute VB_PredeclaredId = True
Attribute VB_Exposed = False
Attribute VB_TemplateDerived = False
Attribute VB_Customizable = False
Private Sub cmdInsert_Click()
Dim find As String
find = txtFind.Text
ThisDrawing.SendCommand ("ReplaceTextOnClick" & vbCr & """" & find & """" & vbCr)
End Sub

Private Sub cmdRenumber_Click()
Dim start, incr, prefix, suffix As String
start = txtStart.Text
incr = txtIncrement.Text
prefix = txtPrefix.Text
suffix = txtSuffix.Text
ThisDrawing.SendCommand ("UpdateTextSequence" & vbCr & start & vbCr & incr & vbCr & prefix & vbCr & suffix & vbCr)
End Sub

Private Sub cmdReplace_Click()
Dim find, replace As String
find = txtFind.Text
replace = txtReplace.Text
ThisDrawing.SendCommand ("FindReplaceTextMTextContd" & vbCr & """" & find & """" & vbCr & """" & replace & """" & vbCr)
End Sub

Private Sub txtFind_Change()

End Sub

Private Sub txtInsert_Change()

End Sub

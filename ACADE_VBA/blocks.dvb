Attribute VB_Name = "Module1"
Sub SwapSpecificBlock()
    Dim doc As AcadDocument
    Set doc = ThisDrawing

    Dim sourceBlockName As String: sourceBlockName = "VCB11_1-"
    Dim targetBlockName As String: targetBlockName = "VCB1_MCCB_CMPOILS"

    Dim blockList As AcadSelectionSet
    Set blockList = doc.SelectionSets.Add("BlockList")
    blockList.Clear
    blockList.Select acSelectionSetAll

    If blockList.Count = 0 Then
        MsgBox "No blocks found in the drawing.", vbExclamation
        Exit Sub
    End If

    Dim obj As AcadEntity
    Dim blockRef As AcadBlockReference
    Dim attributesData As New Collection

    For Each obj In blockList
        If TypeOf obj Is AcadBlockReference Then
            Set blockRef = obj
            If StrComp(blockRef.Name, sourceBlockName, vbTextCompare) = 0 Then

                ' Check if block reference has attributes
                If Not blockRef.HasAttributes Then
                    MsgBox "Block has no attributes.", vbExclamation
                    Exit For
                End If

                Dim attributeRef As AcadAttributeReference
                For Each attributeRef In blockRef.GetAttributes
                    attributesData.Add Array(attributeRef.TagString, attributeRef.TextString)
                Next

                Dim insertionPnt As Variant: insertionPnt = blockRef.InsertionPoint
                blockRef.Delete

                Set blockRef = doc.ModelSpace.InsertBlock(insertionPnt, targetBlockName, 1, 1, 1, 0)

                Dim attributeData As Variant
                For Each attributeData In attributesData
                    For Each attributeRef In blockRef.GetAttributes
                        If attributeRef.TagString = attributeData(0) Then
                            attributeRef.TextString = attributeData(1)
                        End If
                    Next
                Next
            End If
        End If
    Next

    blockList.Delete
    MsgBox "Specific block(s) swapped.", vbInformation
End Sub

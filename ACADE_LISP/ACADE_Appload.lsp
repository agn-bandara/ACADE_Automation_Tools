(vl-vbaload "C:/Users/user/Documents/ACADE_VBA/ACADE_vba_programs.dvb")
(load "C:/Users/user/Documents/ACADE_LISP/ACADE_WireManipulation.lsp")
(load "C:/Users/user/Documents/ACADE_LISP/ACADE_BlockManipulation.lsp")
(load "C:/Users/user/Documents/ACADE_LISP/ACADE_ProjectManipulation.lsp")
(load "C:/Users/user/Documents/ACADE_LISP/ACADE_Audit.lsp")
(load "C:/Users/user/Documents/ACADE_LISP/ACADE_Common.lsp")
(load "C:/Users/user/Documents/ACADE_LISP/ACADE_Automation.lsp")
(load "C:/Users/user/Documents/ACADE_LISP/ACADE_Report.lsp")
(load "C:/Users/user/Documents/ACADE_LISP/ACADE_PanelFootprints.lsp")
(load "C:/Users/user/Documents/ACADE_LISP/ACADE_Support.lsp")
